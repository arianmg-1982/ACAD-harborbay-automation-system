(setq *error* (lambda (msg) (if msg (princ (strcat "\nError: " msg)))))
(setvar "OSMODE" 0)
(command "_.-PURGE" "ALL" "*" "N")
(command "_.REGEN")
(command "VISUALSTYLE" "Wireframe")
(command "_.UNDO" "BEGIN")
(princ "--- INICIO DE DIBUJO AUTOMATIZADO HARBORBAY ---")

; === CREAR CAPAS ===
(princ "\nCreando capas...")
(command "-LAYER" "N" "Niveles" "C" "8" "" "")
(command "-LAYER" "N" "Switches" "C" "6" "" "")
(command "-LAYER" "N" "Textos" "C" "7" "" "")
(command "-LAYER" "N" "Cables_UTP" "C" "5" "" "")
(command "-LAYER" "N" "Fibra_WiFi" "C" "3" "" "")
(command "-LAYER" "N" "Fibra_Telefonia" "C" "4" "" "")
(command "-LAYER" "N" "Fibra_IPTV" "C" "5" "" "")
(command "-LAYER" "N" "Fibra_CCTV" "C" "1" "" "")
(command "-LAYER" "N" "Fibra_Data" "C" "2" "" "")
(command "-LAYER" "N" "APs" "C" "3" "" "")
(command "-LAYER" "N" "Telefonos" "C" "4" "" "")
(command "-LAYER" "N" "TVs" "C" "5" "" "")
(command "-LAYER" "N" "Camaras" "C" "1" "" "")
(command "-LAYER" "N" "Datos" "C" "1" "" "")
(command "-LAYER" "N" "UPS" "C" "1" "" "")
(command "-LAYER" "N" "Estadisticas" "C" "7" "" "")
(princ "DONE.")

; === DIBUJAR NIVELES Y ESTRUCTURA DE TORRES ===
(princ "\nDibujando lineas de Nivel...")
(command "-LAYER" "S" "Niveles" "")
(command "-COLOR" "8")
(command "_.LINE" (list 50 100) (list 16350 100) "")
(command "-LAYER" "S" "Textos" "")
(command "-COLOR" "7")
(command "-TEXT" "S" "Standard" "J" "C" (list 60 110) 15 0 "SOTANO")
(command "-LAYER" "S" "Niveles" "")
(command "-COLOR" "8")
(command "_.LINE" (list 50 300) (list 16350 300) "")
(command "-LAYER" "S" "Textos" "")
(command "-COLOR" "7")
(command "-TEXT" "S" "Standard" "J" "C" (list 60 310) 15 0 "NIVEL1")
(command "-LAYER" "S" "Niveles" "")
(command "-COLOR" "8")
(command "_.LINE" (list 50 500) (list 16350 500) "")
(command "-LAYER" "S" "Textos" "")
(command "-COLOR" "7")
(command "-TEXT" "S" "Standard" "J" "C" (list 60 510) 15 0 "NIVEL2")
(command "-LAYER" "S" "Niveles" "")
(command "-COLOR" "8")
(command "_.LINE" (list 50 700) (list 16350 700) "")
(command "-LAYER" "S" "Textos" "")
(command "-COLOR" "7")
(command "-TEXT" "S" "Standard" "J" "C" (list 60 710) 15 0 "NIVEL3")
(command "-LAYER" "S" "Niveles" "")
(command "-COLOR" "8")
(command "_.LINE" (list 50 900) (list 16350 900) "")
(command "-LAYER" "S" "Textos" "")
(command "-COLOR" "7")
(command "-TEXT" "S" "Standard" "J" "C" (list 60 910) 15 0 "NIVEL4")
(command "-LAYER" "S" "Niveles" "")
(command "-COLOR" "8")
(command "_.LINE" (list 50 1100) (list 16350 1100) "")
(command "-LAYER" "S" "Textos" "")
(command "-COLOR" "7")
(command "-TEXT" "S" "Standard" "J" "C" (list 60 1110) 15 0 "NIVEL5")
(command "-LAYER" "S" "Niveles" "")
(command "-COLOR" "8")
(command "_.LINE" (list 50 1300) (list 16350 1300) "")
(command "-LAYER" "S" "Textos" "")
(command "-COLOR" "7")
(command "-TEXT" "S" "Standard" "J" "C" (list 60 1310) 15 0 "NIVEL6")
(command "-LAYER" "S" "Niveles" "")
(command "-COLOR" "8")
(command "_.LINE" (list 50 1500) (list 16350 1500) "")
(command "-LAYER" "S" "Textos" "")
(command "-COLOR" "7")
(command "-TEXT" "S" "Standard" "J" "C" (list 60 1510) 15 0 "NIVEL7")
(princ "DONE.")

; === DIBUJAR TORRE: MDF ===
(princ "\n>> Dibujando Torre: MDF...")
(command "-LAYER" "S" "Textos" "")
(command "-COLOR" "7")
(command "-TEXT" "S" "Standard" "J" "C" (list 100 150) 25 0 "MDF")
(princ "\n   - Dibujando switches...")
(command "-LAYER" "S" "Switches" "")
(command "-COLOR" "6")
(command "_.PLINE" (list 150 -260) (list 270 -260) (list 270 -220) (list 150 -220) "C")
(command "-LAYER" "S" "Textos" "")
(command "-COLOR" "7")
(command "-TEXT" "S" "Standard" "J" "C" (list 155 -245) 8 0 "SW-CCTV (DS-3E3728F)")
(command "-LAYER" "S" "Switches" "")
(command "-COLOR" "6")
(command "_.PLINE" (list 150 -200) (list 270 -200) (list 270 -160) (list 150 -160) "C")
(command "-LAYER" "S" "Textos" "")
(command "-COLOR" "7")
(command "-TEXT" "S" "Standard" "J" "C" (list 155 -185) 8 0 "SW-DATA (Meraki MS225)")
(command "-LAYER" "S" "Switches" "")
(command "-COLOR" "6")
(command "_.PLINE" (list 150 -140) (list 270 -140) (list 270 -100) (list 150 -100) "C")
(command "-LAYER" "S" "Textos" "")
(command "-COLOR" "7")
(command "-TEXT" "S" "Standard" "J" "C" (list 155 -125) 8 0 "SW-IPTV (RG-NBS6002)")
(command "-LAYER" "S" "Switches" "")
(command "-COLOR" "6")
(command "_.PLINE" (list 150 -80) (list 270 -80) (list 270 -40) (list 150 -40) "C")
(command "-LAYER" "S" "Textos" "")
(command "-COLOR" "7")
(command "-TEXT" "S" "Standard" "J" "C" (list 155 -65) 8 0 "SW-TEL (Meraki MS225)")
(command "-LAYER" "S" "Switches" "")
(command "-COLOR" "6")
(command "_.PLINE" (list 150 -20) (list 270 -20) (list 270 20) (list 150 20) "C")
(command "-LAYER" "S" "Textos" "")
(command "-COLOR" "7")
(command "-TEXT" "S" "Standard" "J" "C" (list 155 -5) 8 0 "SW-UPS (UPS)")
(command "-LAYER" "S" "Switches" "")
(command "-COLOR" "6")
(command "_.PLINE" (list 150 40) (list 270 40) (list 270 80) (list 150 80) "C")
(command "-LAYER" "S" "Textos" "")
(command "-COLOR" "7")
(command "-TEXT" "S" "Standard" "J" "C" (list 155 55) 8 0 "SW-WIFI (Meraki MS225)")
(princ "DONE.")
(princ "\n   - Dibujando UPS...")
(command "-LAYER" "S" "UPS" "")
(command "-COLOR" "1")
(command "_.PLINE" (list 310 -260) (list 390 -260) (list 390 -200) (list 310 -200) "C")
(command "-LAYER" "S" "Textos" "")
(command "-COLOR" "7")
(command "-TEXT" "S" "Standard" "J" "C" (list 335 -235) 15 0 "UPS")
(command "-LAYER" "S" "Textos" "")
(command "-COLOR" "7")
(command "-TEXT" "S" "Standard" "J" "C" (list 315 -280) 10 0 "ALIMENTACION")
(princ "DONE.")
(princ "\n   - Dibujando dispositivos por nivel...")
(command "-LAYER" "S" "APs" "")
(command "-COLOR" "3")
(command "_.PLINE" (list 140.0 150) (list 160.0 150) (list 150 175) (list 140.0 150) "")
(command "_.CIRCLE" (list 150 175) 10)
(command "_.CIRCLE" (list 150 175) 21.25)
(command "_.CIRCLE" (list 150 175) 30)
(command "-LAYER" "S" "Textos" "")
(command "-COLOR" "7")
(command "-TEXT" "S" "Standard" "J" "C" (list 150 130) 10 0 "1xAP")
(princ "DONE.")

; === DIBUJAR TORRE: IDF1 ===
(princ "\n>> Dibujando Torre: IDF1...")
(command "-LAYER" "S" "Textos" "")
(command "-COLOR" "7")
(command "-TEXT" "S" "Standard" "J" "C" (list 1150 150) 25 0 "IDF1")
(princ "\n   - Dibujando switches...")
(command "-LAYER" "S" "Switches" "")
(command "-COLOR" "6")
(command "_.PLINE" (list 1200 -200) (list 1320 -200) (list 1320 -160) (list 1200 -160) "C")
(command "-LAYER" "S" "Textos" "")
(command "-COLOR" "7")
(command "-TEXT" "S" "Standard" "J" "C" (list 1205 -185) 8 0 "SW-CCTV (DS-3E3728F)")
(command "-LAYER" "S" "Switches" "")
(command "-COLOR" "6")
(command "_.PLINE" (list 1200 -140) (list 1320 -140) (list 1320 -100) (list 1200 -100) "C")
(command "-LAYER" "S" "Textos" "")
(command "-COLOR" "7")
(command "-TEXT" "S" "Standard" "J" "C" (list 1205 -125) 8 0 "SW-DATA (Meraki MS225)")
(command "-LAYER" "S" "Switches" "")
(command "-COLOR" "6")
(command "_.PLINE" (list 1200 -80) (list 1320 -80) (list 1320 -40) (list 1200 -40) "C")
(command "-LAYER" "S" "Textos" "")
(command "-COLOR" "7")
(command "-TEXT" "S" "Standard" "J" "C" (list 1205 -65) 8 0 "SW-IPTV (RG-NBS6002)")
(command "-LAYER" "S" "Switches" "")
(command "-COLOR" "6")
(command "_.PLINE" (list 1200 -20) (list 1320 -20) (list 1320 20) (list 1200 20) "C")
(command "-LAYER" "S" "Textos" "")
(command "-COLOR" "7")
(command "-TEXT" "S" "Standard" "J" "C" (list 1205 -5) 8 0 "SW-TEL (Meraki MS225)")
(command "-LAYER" "S" "Switches" "")
(command "-COLOR" "6")
(command "_.PLINE" (list 1200 40) (list 1320 40) (list 1320 80) (list 1200 80) "C")
(command "-LAYER" "S" "Textos" "")
(command "-COLOR" "7")
(command "-TEXT" "S" "Standard" "J" "C" (list 1205 55) 8 0 "SW-WIFI (Meraki MS225)")
(princ "DONE.")
(princ "\n   - Dibujando dispositivos por nivel...")
(command "-LAYER" "S" "APs" "")
(command "-COLOR" "3")
(command "_.PLINE" (list 1190.0 150) (list 1210.0 150) (list 1200 175) (list 1190.0 150) "")
(command "_.CIRCLE" (list 1200 175) 10)
(command "_.CIRCLE" (list 1200 175) 21.25)
(command "_.CIRCLE" (list 1200 175) 30)
(command "-LAYER" "S" "Textos" "")
(command "-COLOR" "7")
(command "-TEXT" "S" "Standard" "J" "C" (list 1200 130) 10 0 "1xAP")
(command "-LAYER" "S" "Telefonos" "")
(command "-COLOR" "4")
(command "_.PLINE" (list 1190.0 350) (list 1210.0 350) (list 1210.0 380) (list 1190.0 380) "C")
(command "_.CIRCLE" (list 1200 387) 5)
(command "-LAYER" "S" "Textos" "")
(command "-COLOR" "7")
(command "-TEXT" "S" "Standard" "J" "C" (list 1200 330) 10 0 "1xTEL")
(command "-LAYER" "S" "TVs" "")
(command "-COLOR" "5")
(command "_.PLINE" (list 1180.0 550) (list 1220.0 550) (list 1220.0 575) (list 1180.0 575) "C")
(command "_.PLINE" (list 1190.0 550) (list 1210.0 550) (list 1200 540) (list 1190.0 550) "")
(command "-LAYER" "S" "Textos" "")
(command "-COLOR" "7")
(command "-TEXT" "S" "Standard" "J" "C" (list 1200 530) 10 0 "1xTV")
(command "-LAYER" "S" "Camaras" "")
(command "-COLOR" "1")
(command "_.PLINE" (list 1190.0 750) (list 1210.0 750) (list 1210.0 765) (list 1190.0 765) "C")
(command "_.CIRCLE" (list 1200 757.5) 3)
(command "-LAYER" "S" "Textos" "")
(command "-COLOR" "7")
(command "-TEXT" "S" "Standard" "J" "C" (list 1200 730) 10 0 "1xCCTV")
(command "-LAYER" "S" "Datos" "")
(command "-COLOR" "1")
(command "_.PLINE" (list 1190.0 950) (list 1210.0 950) (list 1200 970) "C")
(command "-HATCH" "S" "L" "" "")
(command "-LAYER" "S" "Textos" "")
(command "-COLOR" "7")
(command "-TEXT" "S" "Standard" "J" "C" (list 1200 930) 10 0 "1xDATO")
(command "-LAYER" "S" "APs" "")
(command "-COLOR" "3")
(command "_.PLINE" (list 1190.0 1150) (list 1210.0 1150) (list 1200 1175) (list 1190.0 1150) "")
(command "_.CIRCLE" (list 1200 1175) 10)
(command "_.CIRCLE" (list 1200 1175) 21.25)
(command "_.CIRCLE" (list 1200 1175) 30)
(command "-LAYER" "S" "Textos" "")
(command "-COLOR" "7")
(command "-TEXT" "S" "Standard" "J" "C" (list 1200 1130) 10 0 "4xAP")
(command "-LAYER" "S" "Telefonos" "")
(command "-COLOR" "4")
(command "_.PLINE" (list 1290.0 1150) (list 1310.0 1150) (list 1310.0 1180) (list 1290.0 1180) "C")
(command "_.CIRCLE" (list 1300 1187) 5)
(command "-LAYER" "S" "Textos" "")
(command "-COLOR" "7")
(command "-TEXT" "S" "Standard" "J" "C" (list 1300 1130) 10 0 "4xTEL")
(command "-LAYER" "S" "TVs" "")
(command "-COLOR" "5")
(command "_.PLINE" (list 1380.0 1150) (list 1420.0 1150) (list 1420.0 1175) (list 1380.0 1175) "C")
(command "_.PLINE" (list 1390.0 1150) (list 1410.0 1150) (list 1400 1140) (list 1390.0 1150) "")
(command "-LAYER" "S" "Textos" "")
(command "-COLOR" "7")
(command "-TEXT" "S" "Standard" "J" "C" (list 1400 1130) 10 0 "2xTV")
(command "-LAYER" "S" "Camaras" "")
(command "-COLOR" "1")
(command "_.PLINE" (list 1490.0 1150) (list 1510.0 1150) (list 1510.0 1165) (list 1490.0 1165) "C")
(command "_.CIRCLE" (list 1500 1157.5) 3)
(command "-LAYER" "S" "Textos" "")
(command "-COLOR" "7")
(command "-TEXT" "S" "Standard" "J" "C" (list 1500 1130) 10 0 "1xCCTV")
(command "-LAYER" "S" "Datos" "")
(command "-COLOR" "1")
(command "_.PLINE" (list 1590.0 1150) (list 1610.0 1150) (list 1600 1170) "C")
(command "-HATCH" "S" "L" "" "")
(command "-LAYER" "S" "Textos" "")
(command "-COLOR" "7")
(command "-TEXT" "S" "Standard" "J" "C" (list 1600 1130) 10 0 "10xDATO")
(command "-LAYER" "S" "APs" "")
(command "-COLOR" "3")
(command "_.PLINE" (list 1190.0 1350) (list 1210.0 1350) (list 1200 1375) (list 1190.0 1350) "")
(command "_.CIRCLE" (list 1200 1375) 10)
(command "_.CIRCLE" (list 1200 1375) 21.25)
(command "_.CIRCLE" (list 1200 1375) 30)
(command "-LAYER" "S" "Textos" "")
(command "-COLOR" "7")
(command "-TEXT" "S" "Standard" "J" "C" (list 1200 1330) 10 0 "4xAP")
(command "-LAYER" "S" "Telefonos" "")
(command "-COLOR" "4")
(command "_.PLINE" (list 1290.0 1350) (list 1310.0 1350) (list 1310.0 1380) (list 1290.0 1380) "C")
(command "_.CIRCLE" (list 1300 1387) 5)
(command "-LAYER" "S" "Textos" "")
(command "-COLOR" "7")
(command "-TEXT" "S" "Standard" "J" "C" (list 1300 1330) 10 0 "4xTEL")
(command "-LAYER" "S" "TVs" "")
(command "-COLOR" "5")
(command "_.PLINE" (list 1380.0 1350) (list 1420.0 1350) (list 1420.0 1375) (list 1380.0 1375) "C")
(command "_.PLINE" (list 1390.0 1350) (list 1410.0 1350) (list 1400 1340) (list 1390.0 1350) "")
(command "-LAYER" "S" "Textos" "")
(command "-COLOR" "7")
(command "-TEXT" "S" "Standard" "J" "C" (list 1400 1330) 10 0 "2xTV")
(command "-LAYER" "S" "Camaras" "")
(command "-COLOR" "1")
(command "_.PLINE" (list 1490.0 1350) (list 1510.0 1350) (list 1510.0 1365) (list 1490.0 1365) "C")
(command "_.CIRCLE" (list 1500 1357.5) 3)
(command "-LAYER" "S" "Textos" "")
(command "-COLOR" "7")
(command "-TEXT" "S" "Standard" "J" "C" (list 1500 1330) 10 0 "1xCCTV")
(command "-LAYER" "S" "Datos" "")
(command "-COLOR" "1")
(command "_.PLINE" (list 1590.0 1350) (list 1610.0 1350) (list 1600 1370) "C")
(command "-HATCH" "S" "L" "" "")
(command "-LAYER" "S" "Textos" "")
(command "-COLOR" "7")
(command "-TEXT" "S" "Standard" "J" "C" (list 1600 1330) 10 0 "10xDATO")
(command "-LAYER" "S" "APs" "")
(command "-COLOR" "3")
(command "_.PLINE" (list 1190.0 1550) (list 1210.0 1550) (list 1200 1575) (list 1190.0 1550) "")
(command "_.CIRCLE" (list 1200 1575) 10)
(command "_.CIRCLE" (list 1200 1575) 21.25)
(command "_.CIRCLE" (list 1200 1575) 30)
(command "-LAYER" "S" "Textos" "")
(command "-COLOR" "7")
(command "-TEXT" "S" "Standard" "J" "C" (list 1200 1530) 10 0 "2xAP")
(command "-LAYER" "S" "Telefonos" "")
(command "-COLOR" "4")
(command "_.PLINE" (list 1290.0 1550) (list 1310.0 1550) (list 1310.0 1580) (list 1290.0 1580) "C")
(command "_.CIRCLE" (list 1300 1587) 5)
(command "-LAYER" "S" "Textos" "")
(command "-COLOR" "7")
(command "-TEXT" "S" "Standard" "J" "C" (list 1300 1530) 10 0 "2xTEL")
(command "-LAYER" "S" "TVs" "")
(command "-COLOR" "5")
(command "_.PLINE" (list 1380.0 1550) (list 1420.0 1550) (list 1420.0 1575) (list 1380.0 1575) "C")
(command "_.PLINE" (list 1390.0 1550) (list 1410.0 1550) (list 1400 1540) (list 1390.0 1550) "")
(command "-LAYER" "S" "Textos" "")
(command "-COLOR" "7")
(command "-TEXT" "S" "Standard" "J" "C" (list 1400 1530) 10 0 "1xTV")
(command "-LAYER" "S" "Camaras" "")
(command "-COLOR" "1")
(command "_.PLINE" (list 1490.0 1550) (list 1510.0 1550) (list 1510.0 1565) (list 1490.0 1565) "C")
(command "_.CIRCLE" (list 1500 1557.5) 3)
(command "-LAYER" "S" "Textos" "")
(command "-COLOR" "7")
(command "-TEXT" "S" "Standard" "J" "C" (list 1500 1530) 10 0 "1xCCTV")
(command "-LAYER" "S" "Datos" "")
(command "-COLOR" "1")
(command "_.PLINE" (list 1590.0 1550) (list 1610.0 1550) (list 1600 1570) "C")
(command "-HATCH" "S" "L" "" "")
(command "-LAYER" "S" "Textos" "")
(command "-COLOR" "7")
(command "-TEXT" "S" "Standard" "J" "C" (list 1600 1530) 10 0 "6xDATO")
(princ "DONE.")

; === DIBUJAR TORRE: IDF2 ===
(princ "\n>> Dibujando Torre: IDF2...")
(command "-LAYER" "S" "Textos" "")
(command "-COLOR" "7")
(command "-TEXT" "S" "Standard" "J" "C" (list 2200 150) 25 0 "IDF2")
(princ "\n   - Dibujando switches...")
(command "-LAYER" "S" "Switches" "")
(command "-COLOR" "6")
(command "_.PLINE" (list 2250 -200) (list 2370 -200) (list 2370 -160) (list 2250 -160) "C")
(command "-LAYER" "S" "Textos" "")
(command "-COLOR" "7")
(command "-TEXT" "S" "Standard" "J" "C" (list 2255 -185) 8 0 "SW-CCTV (DS-3E3728F)")
(command "-LAYER" "S" "Switches" "")
(command "-COLOR" "6")
(command "_.PLINE" (list 2250 -140) (list 2370 -140) (list 2370 -100) (list 2250 -100) "C")
(command "-LAYER" "S" "Textos" "")
(command "-COLOR" "7")
(command "-TEXT" "S" "Standard" "J" "C" (list 2255 -125) 8 0 "SW-DATA (Meraki MS225)")
(command "-LAYER" "S" "Switches" "")
(command "-COLOR" "6")
(command "_.PLINE" (list 2250 -80) (list 2370 -80) (list 2370 -40) (list 2250 -40) "C")
(command "-LAYER" "S" "Textos" "")
(command "-COLOR" "7")
(command "-TEXT" "S" "Standard" "J" "C" (list 2255 -65) 8 0 "SW-IPTV (RG-NBS6002)")
(command "-LAYER" "S" "Switches" "")
(command "-COLOR" "6")
(command "_.PLINE" (list 2250 -20) (list 2370 -20) (list 2370 20) (list 2250 20) "C")
(command "-LAYER" "S" "Textos" "")
(command "-COLOR" "7")
(command "-TEXT" "S" "Standard" "J" "C" (list 2255 -5) 8 0 "SW-TEL (Meraki MS225)")
(command "-LAYER" "S" "Switches" "")
(command "-COLOR" "6")
(command "_.PLINE" (list 2250 40) (list 2370 40) (list 2370 80) (list 2250 80) "C")
(command "-LAYER" "S" "Textos" "")
(command "-COLOR" "7")
(command "-TEXT" "S" "Standard" "J" "C" (list 2255 55) 8 0 "SW-WIFI (Meraki MS225)")
(princ "DONE.")
(princ "\n   - Dibujando dispositivos por nivel...")
(command "-LAYER" "S" "Telefonos" "")
(command "-COLOR" "4")
(command "_.PLINE" (list 2240.0 150) (list 2260.0 150) (list 2260.0 180) (list 2240.0 180) "C")
(command "_.CIRCLE" (list 2250 187) 5)
(command "-LAYER" "S" "Textos" "")
(command "-COLOR" "7")
(command "-TEXT" "S" "Standard" "J" "C" (list 2250 130) 10 0 "2xTEL")
(command "-LAYER" "S" "TVs" "")
(command "-COLOR" "5")
(command "_.PLINE" (list 2330.0 150) (list 2370.0 150) (list 2370.0 175) (list 2330.0 175) "C")
(command "_.PLINE" (list 2340.0 150) (list 2360.0 150) (list 2350 140) (list 2340.0 150) "")
(command "-LAYER" "S" "Textos" "")
(command "-COLOR" "7")
(command "-TEXT" "S" "Standard" "J" "C" (list 2350 130) 10 0 "1xTV")
(command "-LAYER" "S" "Camaras" "")
(command "-COLOR" "1")
(command "_.PLINE" (list 2440.0 150) (list 2460.0 150) (list 2460.0 165) (list 2440.0 165) "C")
(command "_.CIRCLE" (list 2450 157.5) 3)
(command "-LAYER" "S" "Textos" "")
(command "-COLOR" "7")
(command "-TEXT" "S" "Standard" "J" "C" (list 2450 130) 10 0 "1xCCTV")
(command "-LAYER" "S" "Datos" "")
(command "-COLOR" "1")
(command "_.PLINE" (list 2540.0 150) (list 2560.0 150) (list 2550 170) "C")
(command "-HATCH" "S" "L" "" "")
(command "-LAYER" "S" "Textos" "")
(command "-COLOR" "7")
(command "-TEXT" "S" "Standard" "J" "C" (list 2550 130) 10 0 "4xDATO")
(command "-LAYER" "S" "APs" "")
(command "-COLOR" "3")
(command "_.PLINE" (list 2240.0 350) (list 2260.0 350) (list 2250 375) (list 2240.0 350) "")
(command "_.CIRCLE" (list 2250 375) 10)
(command "_.CIRCLE" (list 2250 375) 21.25)
(command "_.CIRCLE" (list 2250 375) 30)
(command "-LAYER" "S" "Textos" "")
(command "-COLOR" "7")
(command "-TEXT" "S" "Standard" "J" "C" (list 2250 330) 10 0 "5xAP")
(command "-LAYER" "S" "Telefonos" "")
(command "-COLOR" "4")
(command "_.PLINE" (list 2340.0 350) (list 2360.0 350) (list 2360.0 380) (list 2340.0 380) "C")
(command "_.CIRCLE" (list 2350 387) 5)
(command "-LAYER" "S" "Textos" "")
(command "-COLOR" "7")
(command "-TEXT" "S" "Standard" "J" "C" (list 2350 330) 10 0 "6xTEL")
(command "-LAYER" "S" "TVs" "")
(command "-COLOR" "5")
(command "_.PLINE" (list 2430.0 350) (list 2470.0 350) (list 2470.0 375) (list 2430.0 375) "C")
(command "_.PLINE" (list 2440.0 350) (list 2460.0 350) (list 2450 340) (list 2440.0 350) "")
(command "-LAYER" "S" "Textos" "")
(command "-COLOR" "7")
(command "-TEXT" "S" "Standard" "J" "C" (list 2450 330) 10 0 "4xTV")
(command "-LAYER" "S" "Camaras" "")
(command "-COLOR" "1")
(command "_.PLINE" (list 2540.0 350) (list 2560.0 350) (list 2560.0 365) (list 2540.0 365) "C")
(command "_.CIRCLE" (list 2550 357.5) 3)
(command "-LAYER" "S" "Textos" "")
(command "-COLOR" "7")
(command "-TEXT" "S" "Standard" "J" "C" (list 2550 330) 10 0 "2xCCTV")
(command "-LAYER" "S" "Datos" "")
(command "-COLOR" "1")
(command "_.PLINE" (list 2640.0 350) (list 2660.0 350) (list 2650 370) "C")
(command "-HATCH" "S" "L" "" "")
(command "-LAYER" "S" "Textos" "")
(command "-COLOR" "7")
(command "-TEXT" "S" "Standard" "J" "C" (list 2650 330) 10 0 "14xDATO")
(command "-LAYER" "S" "APs" "")
(command "-COLOR" "3")
(command "_.PLINE" (list 2240.0 550) (list 2260.0 550) (list 2250 575) (list 2240.0 550) "")
(command "_.CIRCLE" (list 2250 575) 10)
(command "_.CIRCLE" (list 2250 575) 21.25)
(command "_.CIRCLE" (list 2250 575) 30)
(command "-LAYER" "S" "Textos" "")
(command "-COLOR" "7")
(command "-TEXT" "S" "Standard" "J" "C" (list 2250 530) 10 0 "4xAP")
(command "-LAYER" "S" "Telefonos" "")
(command "-COLOR" "4")
(command "_.PLINE" (list 2340.0 550) (list 2360.0 550) (list 2360.0 580) (list 2340.0 580) "C")
(command "_.CIRCLE" (list 2350 587) 5)
(command "-LAYER" "S" "Textos" "")
(command "-COLOR" "7")
(command "-TEXT" "S" "Standard" "J" "C" (list 2350 530) 10 0 "4xTEL")
(command "-LAYER" "S" "TVs" "")
(command "-COLOR" "5")
(command "_.PLINE" (list 2430.0 550) (list 2470.0 550) (list 2470.0 575) (list 2430.0 575) "C")
(command "_.PLINE" (list 2440.0 550) (list 2460.0 550) (list 2450 540) (list 2440.0 550) "")
(command "-LAYER" "S" "Textos" "")
(command "-COLOR" "7")
(command "-TEXT" "S" "Standard" "J" "C" (list 2450 530) 10 0 "2xTV")
(command "-LAYER" "S" "Camaras" "")
(command "-COLOR" "1")
(command "_.PLINE" (list 2540.0 550) (list 2560.0 550) (list 2560.0 565) (list 2540.0 565) "C")
(command "_.CIRCLE" (list 2550 557.5) 3)
(command "-LAYER" "S" "Textos" "")
(command "-COLOR" "7")
(command "-TEXT" "S" "Standard" "J" "C" (list 2550 530) 10 0 "1xCCTV")
(command "-LAYER" "S" "Datos" "")
(command "-COLOR" "1")
(command "_.PLINE" (list 2640.0 550) (list 2660.0 550) (list 2650 570) "C")
(command "-HATCH" "S" "L" "" "")
(command "-LAYER" "S" "Textos" "")
(command "-COLOR" "7")
(command "-TEXT" "S" "Standard" "J" "C" (list 2650 530) 10 0 "10xDATO")
(command "-LAYER" "S" "APs" "")
(command "-COLOR" "3")
(command "_.PLINE" (list 2240.0 750) (list 2260.0 750) (list 2250 775) (list 2240.0 750) "")
(command "_.CIRCLE" (list 2250 775) 10)
(command "_.CIRCLE" (list 2250 775) 21.25)
(command "_.CIRCLE" (list 2250 775) 30)
(command "-LAYER" "S" "Textos" "")
(command "-COLOR" "7")
(command "-TEXT" "S" "Standard" "J" "C" (list 2250 730) 10 0 "4xAP")
(command "-LAYER" "S" "Telefonos" "")
(command "-COLOR" "4")
(command "_.PLINE" (list 2340.0 750) (list 2360.0 750) (list 2360.0 780) (list 2340.0 780) "C")
(command "_.CIRCLE" (list 2350 787) 5)
(command "-LAYER" "S" "Textos" "")
(command "-COLOR" "7")
(command "-TEXT" "S" "Standard" "J" "C" (list 2350 730) 10 0 "4xTEL")
(command "-LAYER" "S" "TVs" "")
(command "-COLOR" "5")
(command "_.PLINE" (list 2430.0 750) (list 2470.0 750) (list 2470.0 775) (list 2430.0 775) "C")
(command "_.PLINE" (list 2440.0 750) (list 2460.0 750) (list 2450 740) (list 2440.0 750) "")
(command "-LAYER" "S" "Textos" "")
(command "-COLOR" "7")
(command "-TEXT" "S" "Standard" "J" "C" (list 2450 730) 10 0 "2xTV")
(command "-LAYER" "S" "Camaras" "")
(command "-COLOR" "1")
(command "_.PLINE" (list 2540.0 750) (list 2560.0 750) (list 2560.0 765) (list 2540.0 765) "C")
(command "_.CIRCLE" (list 2550 757.5) 3)
(command "-LAYER" "S" "Textos" "")
(command "-COLOR" "7")
(command "-TEXT" "S" "Standard" "J" "C" (list 2550 730) 10 0 "1xCCTV")
(command "-LAYER" "S" "Datos" "")
(command "-COLOR" "1")
(command "_.PLINE" (list 2640.0 750) (list 2660.0 750) (list 2650 770) "C")
(command "-HATCH" "S" "L" "" "")
(command "-LAYER" "S" "Textos" "")
(command "-COLOR" "7")
(command "-TEXT" "S" "Standard" "J" "C" (list 2650 730) 10 0 "10xDATO")
(command "-LAYER" "S" "APs" "")
(command "-COLOR" "3")
(command "_.PLINE" (list 2240.0 950) (list 2260.0 950) (list 2250 975) (list 2240.0 950) "")
(command "_.CIRCLE" (list 2250 975) 10)
(command "_.CIRCLE" (list 2250 975) 21.25)
(command "_.CIRCLE" (list 2250 975) 30)
(command "-LAYER" "S" "Textos" "")
(command "-COLOR" "7")
(command "-TEXT" "S" "Standard" "J" "C" (list 2250 930) 10 0 "4xAP")
(command "-LAYER" "S" "Telefonos" "")
(command "-COLOR" "4")
(command "_.PLINE" (list 2340.0 950) (list 2360.0 950) (list 2360.0 980) (list 2340.0 980) "C")
(command "_.CIRCLE" (list 2350 987) 5)
(command "-LAYER" "S" "Textos" "")
(command "-COLOR" "7")
(command "-TEXT" "S" "Standard" "J" "C" (list 2350 930) 10 0 "4xTEL")
(command "-LAYER" "S" "TVs" "")
(command "-COLOR" "5")
(command "_.PLINE" (list 2430.0 950) (list 2470.0 950) (list 2470.0 975) (list 2430.0 975) "C")
(command "_.PLINE" (list 2440.0 950) (list 2460.0 950) (list 2450 940) (list 2440.0 950) "")
(command "-LAYER" "S" "Textos" "")
(command "-COLOR" "7")
(command "-TEXT" "S" "Standard" "J" "C" (list 2450 930) 10 0 "2xTV")
(command "-LAYER" "S" "Camaras" "")
(command "-COLOR" "1")
(command "_.PLINE" (list 2540.0 950) (list 2560.0 950) (list 2560.0 965) (list 2540.0 965) "C")
(command "_.CIRCLE" (list 2550 957.5) 3)
(command "-LAYER" "S" "Textos" "")
(command "-COLOR" "7")
(command "-TEXT" "S" "Standard" "J" "C" (list 2550 930) 10 0 "1xCCTV")
(command "-LAYER" "S" "Datos" "")
(command "-COLOR" "1")
(command "_.PLINE" (list 2640.0 950) (list 2660.0 950) (list 2650 970) "C")
(command "-HATCH" "S" "L" "" "")
(command "-LAYER" "S" "Textos" "")
(command "-COLOR" "7")
(command "-TEXT" "S" "Standard" "J" "C" (list 2650 930) 10 0 "10xDATO")
(command "-LAYER" "S" "APs" "")
(command "-COLOR" "3")
(command "_.PLINE" (list 2240.0 1150) (list 2260.0 1150) (list 2250 1175) (list 2240.0 1150) "")
(command "_.CIRCLE" (list 2250 1175) 10)
(command "_.CIRCLE" (list 2250 1175) 21.25)
(command "_.CIRCLE" (list 2250 1175) 30)
(command "-LAYER" "S" "Textos" "")
(command "-COLOR" "7")
(command "-TEXT" "S" "Standard" "J" "C" (list 2250 1130) 10 0 "4xAP")
(command "-LAYER" "S" "Telefonos" "")
(command "-COLOR" "4")
(command "_.PLINE" (list 2340.0 1150) (list 2360.0 1150) (list 2360.0 1180) (list 2340.0 1180) "C")
(command "_.CIRCLE" (list 2350 1187) 5)
(command "-LAYER" "S" "Textos" "")
(command "-COLOR" "7")
(command "-TEXT" "S" "Standard" "J" "C" (list 2350 1130) 10 0 "4xTEL")
(command "-LAYER" "S" "TVs" "")
(command "-COLOR" "5")
(command "_.PLINE" (list 2430.0 1150) (list 2470.0 1150) (list 2470.0 1175) (list 2430.0 1175) "C")
(command "_.PLINE" (list 2440.0 1150) (list 2460.0 1150) (list 2450 1140) (list 2440.0 1150) "")
(command "-LAYER" "S" "Textos" "")
(command "-COLOR" "7")
(command "-TEXT" "S" "Standard" "J" "C" (list 2450 1130) 10 0 "2xTV")
(command "-LAYER" "S" "Camaras" "")
(command "-COLOR" "1")
(command "_.PLINE" (list 2540.0 1150) (list 2560.0 1150) (list 2560.0 1165) (list 2540.0 1165) "C")
(command "_.CIRCLE" (list 2550 1157.5) 3)
(command "-LAYER" "S" "Textos" "")
(command "-COLOR" "7")
(command "-TEXT" "S" "Standard" "J" "C" (list 2550 1130) 10 0 "1xCCTV")
(command "-LAYER" "S" "Datos" "")
(command "-COLOR" "1")
(command "_.PLINE" (list 2640.0 1150) (list 2660.0 1150) (list 2650 1170) "C")
(command "-HATCH" "S" "L" "" "")
(command "-LAYER" "S" "Textos" "")
(command "-COLOR" "7")
(command "-TEXT" "S" "Standard" "J" "C" (list 2650 1130) 10 0 "10xDATO")
(command "-LAYER" "S" "APs" "")
(command "-COLOR" "3")
(command "_.PLINE" (list 2240.0 1350) (list 2260.0 1350) (list 2250 1375) (list 2240.0 1350) "")
(command "_.CIRCLE" (list 2250 1375) 10)
(command "_.CIRCLE" (list 2250 1375) 21.25)
(command "_.CIRCLE" (list 2250 1375) 30)
(command "-LAYER" "S" "Textos" "")
(command "-COLOR" "7")
(command "-TEXT" "S" "Standard" "J" "C" (list 2250 1330) 10 0 "4xAP")
(command "-LAYER" "S" "Telefonos" "")
(command "-COLOR" "4")
(command "_.PLINE" (list 2340.0 1350) (list 2360.0 1350) (list 2360.0 1380) (list 2340.0 1380) "C")
(command "_.CIRCLE" (list 2350 1387) 5)
(command "-LAYER" "S" "Textos" "")
(command "-COLOR" "7")
(command "-TEXT" "S" "Standard" "J" "C" (list 2350 1330) 10 0 "4xTEL")
(command "-LAYER" "S" "TVs" "")
(command "-COLOR" "5")
(command "_.PLINE" (list 2430.0 1350) (list 2470.0 1350) (list 2470.0 1375) (list 2430.0 1375) "C")
(command "_.PLINE" (list 2440.0 1350) (list 2460.0 1350) (list 2450 1340) (list 2440.0 1350) "")
(command "-LAYER" "S" "Textos" "")
(command "-COLOR" "7")
(command "-TEXT" "S" "Standard" "J" "C" (list 2450 1330) 10 0 "2xTV")
(command "-LAYER" "S" "Camaras" "")
(command "-COLOR" "1")
(command "_.PLINE" (list 2540.0 1350) (list 2560.0 1350) (list 2560.0 1365) (list 2540.0 1365) "C")
(command "_.CIRCLE" (list 2550 1357.5) 3)
(command "-LAYER" "S" "Textos" "")
(command "-COLOR" "7")
(command "-TEXT" "S" "Standard" "J" "C" (list 2550 1330) 10 0 "1xCCTV")
(command "-LAYER" "S" "Datos" "")
(command "-COLOR" "1")
(command "_.PLINE" (list 2640.0 1350) (list 2660.0 1350) (list 2650 1370) "C")
(command "-HATCH" "S" "L" "" "")
(command "-LAYER" "S" "Textos" "")
(command "-COLOR" "7")
(command "-TEXT" "S" "Standard" "J" "C" (list 2650 1330) 10 0 "10xDATO")
(command "-LAYER" "S" "APs" "")
(command "-COLOR" "3")
(command "_.PLINE" (list 2240.0 1550) (list 2260.0 1550) (list 2250 1575) (list 2240.0 1550) "")
(command "_.CIRCLE" (list 2250 1575) 10)
(command "_.CIRCLE" (list 2250 1575) 21.25)
(command "_.CIRCLE" (list 2250 1575) 30)
(command "-LAYER" "S" "Textos" "")
(command "-COLOR" "7")
(command "-TEXT" "S" "Standard" "J" "C" (list 2250 1530) 10 0 "2xAP")
(command "-LAYER" "S" "Telefonos" "")
(command "-COLOR" "4")
(command "_.PLINE" (list 2340.0 1550) (list 2360.0 1550) (list 2360.0 1580) (list 2340.0 1580) "C")
(command "_.CIRCLE" (list 2350 1587) 5)
(command "-LAYER" "S" "Textos" "")
(command "-COLOR" "7")
(command "-TEXT" "S" "Standard" "J" "C" (list 2350 1530) 10 0 "2xTEL")
(command "-LAYER" "S" "TVs" "")
(command "-COLOR" "5")
(command "_.PLINE" (list 2430.0 1550) (list 2470.0 1550) (list 2470.0 1575) (list 2430.0 1575) "C")
(command "_.PLINE" (list 2440.0 1550) (list 2460.0 1550) (list 2450 1540) (list 2440.0 1550) "")
(command "-LAYER" "S" "Textos" "")
(command "-COLOR" "7")
(command "-TEXT" "S" "Standard" "J" "C" (list 2450 1530) 10 0 "1xTV")
(command "-LAYER" "S" "Camaras" "")
(command "-COLOR" "1")
(command "_.PLINE" (list 2540.0 1550) (list 2560.0 1550) (list 2560.0 1565) (list 2540.0 1565) "C")
(command "_.CIRCLE" (list 2550 1557.5) 3)
(command "-LAYER" "S" "Textos" "")
(command "-COLOR" "7")
(command "-TEXT" "S" "Standard" "J" "C" (list 2550 1530) 10 0 "1xCCTV")
(command "-LAYER" "S" "Datos" "")
(command "-COLOR" "1")
(command "_.PLINE" (list 2640.0 1550) (list 2660.0 1550) (list 2650 1570) "C")
(command "-HATCH" "S" "L" "" "")
(command "-LAYER" "S" "Textos" "")
(command "-COLOR" "7")
(command "-TEXT" "S" "Standard" "J" "C" (list 2650 1530) 10 0 "6xDATO")
(princ "DONE.")

; === DIBUJAR TORRE: IDF3 ===
(princ "\n>> Dibujando Torre: IDF3...")
(command "-LAYER" "S" "Textos" "")
(command "-COLOR" "7")
(command "-TEXT" "S" "Standard" "J" "C" (list 3250 150) 25 0 "IDF3")
(princ "\n   - Dibujando switches...")
(command "-LAYER" "S" "Switches" "")
(command "-COLOR" "6")
(command "_.PLINE" (list 3300 -200) (list 3420 -200) (list 3420 -160) (list 3300 -160) "C")
(command "-LAYER" "S" "Textos" "")
(command "-COLOR" "7")
(command "-TEXT" "S" "Standard" "J" "C" (list 3305 -185) 8 0 "SW-CCTV (DS-3E3728F)")
(command "-LAYER" "S" "Switches" "")
(command "-COLOR" "6")
(command "_.PLINE" (list 3300 -140) (list 3420 -140) (list 3420 -100) (list 3300 -100) "C")
(command "-LAYER" "S" "Textos" "")
(command "-COLOR" "7")
(command "-TEXT" "S" "Standard" "J" "C" (list 3305 -125) 8 0 "SW-DATA (Meraki MS225)")
(command "-LAYER" "S" "Switches" "")
(command "-COLOR" "6")
(command "_.PLINE" (list 3300 -80) (list 3420 -80) (list 3420 -40) (list 3300 -40) "C")
(command "-LAYER" "S" "Textos" "")
(command "-COLOR" "7")
(command "-TEXT" "S" "Standard" "J" "C" (list 3305 -65) 8 0 "SW-IPTV (RG-NBS6002)")
(command "-LAYER" "S" "Switches" "")
(command "-COLOR" "6")
(command "_.PLINE" (list 3300 -20) (list 3420 -20) (list 3420 20) (list 3300 20) "C")
(command "-LAYER" "S" "Textos" "")
(command "-COLOR" "7")
(command "-TEXT" "S" "Standard" "J" "C" (list 3305 -5) 8 0 "SW-TEL (Meraki MS225)")
(command "-LAYER" "S" "Switches" "")
(command "-COLOR" "6")
(command "_.PLINE" (list 3300 40) (list 3420 40) (list 3420 80) (list 3300 80) "C")
(command "-LAYER" "S" "Textos" "")
(command "-COLOR" "7")
(command "-TEXT" "S" "Standard" "J" "C" (list 3305 55) 8 0 "SW-WIFI (Meraki MS225)")
(princ "DONE.")
(princ "\n   - Dibujando dispositivos por nivel...")
(command "-LAYER" "S" "APs" "")
(command "-COLOR" "3")
(command "_.PLINE" (list 3290.0 150) (list 3310.0 150) (list 3300 175) (list 3290.0 150) "")
(command "_.CIRCLE" (list 3300 175) 10)
(command "_.CIRCLE" (list 3300 175) 21.25)
(command "_.CIRCLE" (list 3300 175) 30)
(command "-LAYER" "S" "Textos" "")
(command "-COLOR" "7")
(command "-TEXT" "S" "Standard" "J" "C" (list 3300 130) 10 0 "1xAP")
(command "-LAYER" "S" "Telefonos" "")
(command "-COLOR" "4")
(command "_.PLINE" (list 3390.0 150) (list 3410.0 150) (list 3410.0 180) (list 3390.0 180) "C")
(command "_.CIRCLE" (list 3400 187) 5)
(command "-LAYER" "S" "Textos" "")
(command "-COLOR" "7")
(command "-TEXT" "S" "Standard" "J" "C" (list 3400 130) 10 0 "2xTEL")
(command "-LAYER" "S" "TVs" "")
(command "-COLOR" "5")
(command "_.PLINE" (list 3480.0 150) (list 3520.0 150) (list 3520.0 175) (list 3480.0 175) "C")
(command "_.PLINE" (list 3490.0 150) (list 3510.0 150) (list 3500 140) (list 3490.0 150) "")
(command "-LAYER" "S" "Textos" "")
(command "-COLOR" "7")
(command "-TEXT" "S" "Standard" "J" "C" (list 3500 130) 10 0 "1xTV")
(command "-LAYER" "S" "Camaras" "")
(command "-COLOR" "1")
(command "_.PLINE" (list 3590.0 150) (list 3610.0 150) (list 3610.0 165) (list 3590.0 165) "C")
(command "_.CIRCLE" (list 3600 157.5) 3)
(command "-LAYER" "S" "Textos" "")
(command "-COLOR" "7")
(command "-TEXT" "S" "Standard" "J" "C" (list 3600 130) 10 0 "1xCCTV")
(command "-LAYER" "S" "Datos" "")
(command "-COLOR" "1")
(command "_.PLINE" (list 3690.0 150) (list 3710.0 150) (list 3700 170) "C")
(command "-HATCH" "S" "L" "" "")
(command "-LAYER" "S" "Textos" "")
(command "-COLOR" "7")
(command "-TEXT" "S" "Standard" "J" "C" (list 3700 130) 10 0 "5xDATO")
(command "-LAYER" "S" "APs" "")
(command "-COLOR" "3")
(command "_.PLINE" (list 3290.0 350) (list 3310.0 350) (list 3300 375) (list 3290.0 350) "")
(command "_.CIRCLE" (list 3300 375) 10)
(command "_.CIRCLE" (list 3300 375) 21.25)
(command "_.CIRCLE" (list 3300 375) 30)
(command "-LAYER" "S" "Textos" "")
(command "-COLOR" "7")
(command "-TEXT" "S" "Standard" "J" "C" (list 3300 330) 10 0 "4xAP")
(command "-LAYER" "S" "Telefonos" "")
(command "-COLOR" "4")
(command "_.PLINE" (list 3390.0 350) (list 3410.0 350) (list 3410.0 380) (list 3390.0 380) "C")
(command "_.CIRCLE" (list 3400 387) 5)
(command "-LAYER" "S" "Textos" "")
(command "-COLOR" "7")
(command "-TEXT" "S" "Standard" "J" "C" (list 3400 330) 10 0 "5xTEL")
(command "-LAYER" "S" "TVs" "")
(command "-COLOR" "5")
(command "_.PLINE" (list 3480.0 350) (list 3520.0 350) (list 3520.0 375) (list 3480.0 375) "C")
(command "_.PLINE" (list 3490.0 350) (list 3510.0 350) (list 3500 340) (list 3490.0 350) "")
(command "-LAYER" "S" "Textos" "")
(command "-COLOR" "7")
(command "-TEXT" "S" "Standard" "J" "C" (list 3500 330) 10 0 "3xTV")
(command "-LAYER" "S" "Camaras" "")
(command "-COLOR" "1")
(command "_.PLINE" (list 3590.0 350) (list 3610.0 350) (list 3610.0 365) (list 3590.0 365) "C")
(command "_.CIRCLE" (list 3600 357.5) 3)
(command "-LAYER" "S" "Textos" "")
(command "-COLOR" "7")
(command "-TEXT" "S" "Standard" "J" "C" (list 3600 330) 10 0 "2xCCTV")
(command "-LAYER" "S" "Datos" "")
(command "-COLOR" "1")
(command "_.PLINE" (list 3690.0 350) (list 3710.0 350) (list 3700 370) "C")
(command "-HATCH" "S" "L" "" "")
(command "-LAYER" "S" "Textos" "")
(command "-COLOR" "7")
(command "-TEXT" "S" "Standard" "J" "C" (list 3700 330) 10 0 "12xDATO")
(command "-LAYER" "S" "APs" "")
(command "-COLOR" "3")
(command "_.PLINE" (list 3290.0 550) (list 3310.0 550) (list 3300 575) (list 3290.0 550) "")
(command "_.CIRCLE" (list 3300 575) 10)
(command "_.CIRCLE" (list 3300 575) 21.25)
(command "_.CIRCLE" (list 3300 575) 30)
(command "-LAYER" "S" "Textos" "")
(command "-COLOR" "7")
(command "-TEXT" "S" "Standard" "J" "C" (list 3300 530) 10 0 "4xAP")
(command "-LAYER" "S" "Telefonos" "")
(command "-COLOR" "4")
(command "_.PLINE" (list 3390.0 550) (list 3410.0 550) (list 3410.0 580) (list 3390.0 580) "C")
(command "_.CIRCLE" (list 3400 587) 5)
(command "-LAYER" "S" "Textos" "")
(command "-COLOR" "7")
(command "-TEXT" "S" "Standard" "J" "C" (list 3400 530) 10 0 "4xTEL")
(command "-LAYER" "S" "TVs" "")
(command "-COLOR" "5")
(command "_.PLINE" (list 3480.0 550) (list 3520.0 550) (list 3520.0 575) (list 3480.0 575) "C")
(command "_.PLINE" (list 3490.0 550) (list 3510.0 550) (list 3500 540) (list 3490.0 550) "")
(command "-LAYER" "S" "Textos" "")
(command "-COLOR" "7")
(command "-TEXT" "S" "Standard" "J" "C" (list 3500 530) 10 0 "2xTV")
(command "-LAYER" "S" "Camaras" "")
(command "-COLOR" "1")
(command "_.PLINE" (list 3590.0 550) (list 3610.0 550) (list 3610.0 565) (list 3590.0 565) "C")
(command "_.CIRCLE" (list 3600 557.5) 3)
(command "-LAYER" "S" "Textos" "")
(command "-COLOR" "7")
(command "-TEXT" "S" "Standard" "J" "C" (list 3600 530) 10 0 "1xCCTV")
(command "-LAYER" "S" "Datos" "")
(command "-COLOR" "1")
(command "_.PLINE" (list 3690.0 550) (list 3710.0 550) (list 3700 570) "C")
(command "-HATCH" "S" "L" "" "")
(command "-LAYER" "S" "Textos" "")
(command "-COLOR" "7")
(command "-TEXT" "S" "Standard" "J" "C" (list 3700 530) 10 0 "10xDATO")
(command "-LAYER" "S" "APs" "")
(command "-COLOR" "3")
(command "_.PLINE" (list 3290.0 750) (list 3310.0 750) (list 3300 775) (list 3290.0 750) "")
(command "_.CIRCLE" (list 3300 775) 10)
(command "_.CIRCLE" (list 3300 775) 21.25)
(command "_.CIRCLE" (list 3300 775) 30)
(command "-LAYER" "S" "Textos" "")
(command "-COLOR" "7")
(command "-TEXT" "S" "Standard" "J" "C" (list 3300 730) 10 0 "4xAP")
(command "-LAYER" "S" "Telefonos" "")
(command "-COLOR" "4")
(command "_.PLINE" (list 3390.0 750) (list 3410.0 750) (list 3410.0 780) (list 3390.0 780) "C")
(command "_.CIRCLE" (list 3400 787) 5)
(command "-LAYER" "S" "Textos" "")
(command "-COLOR" "7")
(command "-TEXT" "S" "Standard" "J" "C" (list 3400 730) 10 0 "4xTEL")
(command "-LAYER" "S" "TVs" "")
(command "-COLOR" "5")
(command "_.PLINE" (list 3480.0 750) (list 3520.0 750) (list 3520.0 775) (list 3480.0 775) "C")
(command "_.PLINE" (list 3490.0 750) (list 3510.0 750) (list 3500 740) (list 3490.0 750) "")
(command "-LAYER" "S" "Textos" "")
(command "-COLOR" "7")
(command "-TEXT" "S" "Standard" "J" "C" (list 3500 730) 10 0 "2xTV")
(command "-LAYER" "S" "Camaras" "")
(command "-COLOR" "1")
(command "_.PLINE" (list 3590.0 750) (list 3610.0 750) (list 3610.0 765) (list 3590.0 765) "C")
(command "_.CIRCLE" (list 3600 757.5) 3)
(command "-LAYER" "S" "Textos" "")
(command "-COLOR" "7")
(command "-TEXT" "S" "Standard" "J" "C" (list 3600 730) 10 0 "1xCCTV")
(command "-LAYER" "S" "Datos" "")
(command "-COLOR" "1")
(command "_.PLINE" (list 3690.0 750) (list 3710.0 750) (list 3700 770) "C")
(command "-HATCH" "S" "L" "" "")
(command "-LAYER" "S" "Textos" "")
(command "-COLOR" "7")
(command "-TEXT" "S" "Standard" "J" "C" (list 3700 730) 10 0 "10xDATO")
(command "-LAYER" "S" "APs" "")
(command "-COLOR" "3")
(command "_.PLINE" (list 3290.0 950) (list 3310.0 950) (list 3300 975) (list 3290.0 950) "")
(command "_.CIRCLE" (list 3300 975) 10)
(command "_.CIRCLE" (list 3300 975) 21.25)
(command "_.CIRCLE" (list 3300 975) 30)
(command "-LAYER" "S" "Textos" "")
(command "-COLOR" "7")
(command "-TEXT" "S" "Standard" "J" "C" (list 3300 930) 10 0 "4xAP")
(command "-LAYER" "S" "Telefonos" "")
(command "-COLOR" "4")
(command "_.PLINE" (list 3390.0 950) (list 3410.0 950) (list 3410.0 980) (list 3390.0 980) "C")
(command "_.CIRCLE" (list 3400 987) 5)
(command "-LAYER" "S" "Textos" "")
(command "-COLOR" "7")
(command "-TEXT" "S" "Standard" "J" "C" (list 3400 930) 10 0 "4xTEL")
(command "-LAYER" "S" "TVs" "")
(command "-COLOR" "5")
(command "_.PLINE" (list 3480.0 950) (list 3520.0 950) (list 3520.0 975) (list 3480.0 975) "C")
(command "_.PLINE" (list 3490.0 950) (list 3510.0 950) (list 3500 940) (list 3490.0 950) "")
(command "-LAYER" "S" "Textos" "")
(command "-COLOR" "7")
(command "-TEXT" "S" "Standard" "J" "C" (list 3500 930) 10 0 "2xTV")
(command "-LAYER" "S" "Camaras" "")
(command "-COLOR" "1")
(command "_.PLINE" (list 3590.0 950) (list 3610.0 950) (list 3610.0 965) (list 3590.0 965) "C")
(command "_.CIRCLE" (list 3600 957.5) 3)
(command "-LAYER" "S" "Textos" "")
(command "-COLOR" "7")
(command "-TEXT" "S" "Standard" "J" "C" (list 3600 930) 10 0 "1xCCTV")
(command "-LAYER" "S" "Datos" "")
(command "-COLOR" "1")
(command "_.PLINE" (list 3690.0 950) (list 3710.0 950) (list 3700 970) "C")
(command "-HATCH" "S" "L" "" "")
(command "-LAYER" "S" "Textos" "")
(command "-COLOR" "7")
(command "-TEXT" "S" "Standard" "J" "C" (list 3700 930) 10 0 "10xDATO")
(command "-LAYER" "S" "APs" "")
(command "-COLOR" "3")
(command "_.PLINE" (list 3290.0 1150) (list 3310.0 1150) (list 3300 1175) (list 3290.0 1150) "")
(command "_.CIRCLE" (list 3300 1175) 10)
(command "_.CIRCLE" (list 3300 1175) 21.25)
(command "_.CIRCLE" (list 3300 1175) 30)
(command "-LAYER" "S" "Textos" "")
(command "-COLOR" "7")
(command "-TEXT" "S" "Standard" "J" "C" (list 3300 1130) 10 0 "4xAP")
(command "-LAYER" "S" "Telefonos" "")
(command "-COLOR" "4")
(command "_.PLINE" (list 3390.0 1150) (list 3410.0 1150) (list 3410.0 1180) (list 3390.0 1180) "C")
(command "_.CIRCLE" (list 3400 1187) 5)
(command "-LAYER" "S" "Textos" "")
(command "-COLOR" "7")
(command "-TEXT" "S" "Standard" "J" "C" (list 3400 1130) 10 0 "4xTEL")
(command "-LAYER" "S" "TVs" "")
(command "-COLOR" "5")
(command "_.PLINE" (list 3480.0 1150) (list 3520.0 1150) (list 3520.0 1175) (list 3480.0 1175) "C")
(command "_.PLINE" (list 3490.0 1150) (list 3510.0 1150) (list 3500 1140) (list 3490.0 1150) "")
(command "-LAYER" "S" "Textos" "")
(command "-COLOR" "7")
(command "-TEXT" "S" "Standard" "J" "C" (list 3500 1130) 10 0 "2xTV")
(command "-LAYER" "S" "Camaras" "")
(command "-COLOR" "1")
(command "_.PLINE" (list 3590.0 1150) (list 3610.0 1150) (list 3610.0 1165) (list 3590.0 1165) "C")
(command "_.CIRCLE" (list 3600 1157.5) 3)
(command "-LAYER" "S" "Textos" "")
(command "-COLOR" "7")
(command "-TEXT" "S" "Standard" "J" "C" (list 3600 1130) 10 0 "1xCCTV")
(command "-LAYER" "S" "Datos" "")
(command "-COLOR" "1")
(command "_.PLINE" (list 3690.0 1150) (list 3710.0 1150) (list 3700 1170) "C")
(command "-HATCH" "S" "L" "" "")
(command "-LAYER" "S" "Textos" "")
(command "-COLOR" "7")
(command "-TEXT" "S" "Standard" "J" "C" (list 3700 1130) 10 0 "10xDATO")
(command "-LAYER" "S" "APs" "")
(command "-COLOR" "3")
(command "_.PLINE" (list 3290.0 1350) (list 3310.0 1350) (list 3300 1375) (list 3290.0 1350) "")
(command "_.CIRCLE" (list 3300 1375) 10)
(command "_.CIRCLE" (list 3300 1375) 21.25)
(command "_.CIRCLE" (list 3300 1375) 30)
(command "-LAYER" "S" "Textos" "")
(command "-COLOR" "7")
(command "-TEXT" "S" "Standard" "J" "C" (list 3300 1330) 10 0 "4xAP")
(command "-LAYER" "S" "Telefonos" "")
(command "-COLOR" "4")
(command "_.PLINE" (list 3390.0 1350) (list 3410.0 1350) (list 3410.0 1380) (list 3390.0 1380) "C")
(command "_.CIRCLE" (list 3400 1387) 5)
(command "-LAYER" "S" "Textos" "")
(command "-COLOR" "7")
(command "-TEXT" "S" "Standard" "J" "C" (list 3400 1330) 10 0 "4xTEL")
(command "-LAYER" "S" "TVs" "")
(command "-COLOR" "5")
(command "_.PLINE" (list 3480.0 1350) (list 3520.0 1350) (list 3520.0 1375) (list 3480.0 1375) "C")
(command "_.PLINE" (list 3490.0 1350) (list 3510.0 1350) (list 3500 1340) (list 3490.0 1350) "")
(command "-LAYER" "S" "Textos" "")
(command "-COLOR" "7")
(command "-TEXT" "S" "Standard" "J" "C" (list 3500 1330) 10 0 "2xTV")
(command "-LAYER" "S" "Camaras" "")
(command "-COLOR" "1")
(command "_.PLINE" (list 3590.0 1350) (list 3610.0 1350) (list 3610.0 1365) (list 3590.0 1365) "C")
(command "_.CIRCLE" (list 3600 1357.5) 3)
(command "-LAYER" "S" "Textos" "")
(command "-COLOR" "7")
(command "-TEXT" "S" "Standard" "J" "C" (list 3600 1330) 10 0 "1xCCTV")
(command "-LAYER" "S" "Datos" "")
(command "-COLOR" "1")
(command "_.PLINE" (list 3690.0 1350) (list 3710.0 1350) (list 3700 1370) "C")
(command "-HATCH" "S" "L" "" "")
(command "-LAYER" "S" "Textos" "")
(command "-COLOR" "7")
(command "-TEXT" "S" "Standard" "J" "C" (list 3700 1330) 10 0 "10xDATO")
(command "-LAYER" "S" "APs" "")
(command "-COLOR" "3")
(command "_.PLINE" (list 3290.0 1550) (list 3310.0 1550) (list 3300 1575) (list 3290.0 1550) "")
(command "_.CIRCLE" (list 3300 1575) 10)
(command "_.CIRCLE" (list 3300 1575) 21.25)
(command "_.CIRCLE" (list 3300 1575) 30)
(command "-LAYER" "S" "Textos" "")
(command "-COLOR" "7")
(command "-TEXT" "S" "Standard" "J" "C" (list 3300 1530) 10 0 "2xAP")
(command "-LAYER" "S" "Telefonos" "")
(command "-COLOR" "4")
(command "_.PLINE" (list 3390.0 1550) (list 3410.0 1550) (list 3410.0 1580) (list 3390.0 1580) "C")
(command "_.CIRCLE" (list 3400 1587) 5)
(command "-LAYER" "S" "Textos" "")
(command "-COLOR" "7")
(command "-TEXT" "S" "Standard" "J" "C" (list 3400 1530) 10 0 "2xTEL")
(command "-LAYER" "S" "TVs" "")
(command "-COLOR" "5")
(command "_.PLINE" (list 3480.0 1550) (list 3520.0 1550) (list 3520.0 1575) (list 3480.0 1575) "C")
(command "_.PLINE" (list 3490.0 1550) (list 3510.0 1550) (list 3500 1540) (list 3490.0 1550) "")
(command "-LAYER" "S" "Textos" "")
(command "-COLOR" "7")
(command "-TEXT" "S" "Standard" "J" "C" (list 3500 1530) 10 0 "1xTV")
(command "-LAYER" "S" "Camaras" "")
(command "-COLOR" "1")
(command "_.PLINE" (list 3590.0 1550) (list 3610.0 1550) (list 3610.0 1565) (list 3590.0 1565) "C")
(command "_.CIRCLE" (list 3600 1557.5) 3)
(command "-LAYER" "S" "Textos" "")
(command "-COLOR" "7")
(command "-TEXT" "S" "Standard" "J" "C" (list 3600 1530) 10 0 "1xCCTV")
(command "-LAYER" "S" "Datos" "")
(command "-COLOR" "1")
(command "_.PLINE" (list 3690.0 1550) (list 3710.0 1550) (list 3700 1570) "C")
(command "-HATCH" "S" "L" "" "")
(command "-LAYER" "S" "Textos" "")
(command "-COLOR" "7")
(command "-TEXT" "S" "Standard" "J" "C" (list 3700 1530) 10 0 "6xDATO")
(princ "DONE.")

; === DIBUJAR TORRE: IDF4 ===
(princ "\n>> Dibujando Torre: IDF4...")
(command "-LAYER" "S" "Textos" "")
(command "-COLOR" "7")
(command "-TEXT" "S" "Standard" "J" "C" (list 4300 150) 25 0 "IDF4")
(princ "\n   - Dibujando switches...")
(command "-LAYER" "S" "Switches" "")
(command "-COLOR" "6")
(command "_.PLINE" (list 4350 -200) (list 4470 -200) (list 4470 -160) (list 4350 -160) "C")
(command "-LAYER" "S" "Textos" "")
(command "-COLOR" "7")
(command "-TEXT" "S" "Standard" "J" "C" (list 4355 -185) 8 0 "SW-CCTV (DS-3E3728F)")
(command "-LAYER" "S" "Switches" "")
(command "-COLOR" "6")
(command "_.PLINE" (list 4350 -140) (list 4470 -140) (list 4470 -100) (list 4350 -100) "C")
(command "-LAYER" "S" "Textos" "")
(command "-COLOR" "7")
(command "-TEXT" "S" "Standard" "J" "C" (list 4355 -125) 8 0 "SW-DATA (Meraki MS225)")
(command "-LAYER" "S" "Switches" "")
(command "-COLOR" "6")
(command "_.PLINE" (list 4350 -80) (list 4470 -80) (list 4470 -40) (list 4350 -40) "C")
(command "-LAYER" "S" "Textos" "")
(command "-COLOR" "7")
(command "-TEXT" "S" "Standard" "J" "C" (list 4355 -65) 8 0 "SW-IPTV (RG-NBS6002)")
(command "-LAYER" "S" "Switches" "")
(command "-COLOR" "6")
(command "_.PLINE" (list 4350 -20) (list 4470 -20) (list 4470 20) (list 4350 20) "C")
(command "-LAYER" "S" "Textos" "")
(command "-COLOR" "7")
(command "-TEXT" "S" "Standard" "J" "C" (list 4355 -5) 8 0 "SW-TEL (Meraki MS225)")
(command "-LAYER" "S" "Switches" "")
(command "-COLOR" "6")
(command "_.PLINE" (list 4350 40) (list 4470 40) (list 4470 80) (list 4350 80) "C")
(command "-LAYER" "S" "Textos" "")
(command "-COLOR" "7")
(command "-TEXT" "S" "Standard" "J" "C" (list 4355 55) 8 0 "SW-WIFI (Meraki MS225)")
(princ "DONE.")
(princ "\n   - Dibujando dispositivos por nivel...")
(command "-LAYER" "S" "Telefonos" "")
(command "-COLOR" "4")
(command "_.PLINE" (list 4340.0 150) (list 4360.0 150) (list 4360.0 180) (list 4340.0 180) "C")
(command "_.CIRCLE" (list 4350 187) 5)
(command "-LAYER" "S" "Textos" "")
(command "-COLOR" "7")
(command "-TEXT" "S" "Standard" "J" "C" (list 4350 130) 10 0 "1xTEL")
(command "-LAYER" "S" "Camaras" "")
(command "-COLOR" "1")
(command "_.PLINE" (list 4440.0 150) (list 4460.0 150) (list 4460.0 165) (list 4440.0 165) "C")
(command "_.CIRCLE" (list 4450 157.5) 3)
(command "-LAYER" "S" "Textos" "")
(command "-COLOR" "7")
(command "-TEXT" "S" "Standard" "J" "C" (list 4450 130) 10 0 "1xCCTV")
(command "-LAYER" "S" "Datos" "")
(command "-COLOR" "1")
(command "_.PLINE" (list 4540.0 150) (list 4560.0 150) (list 4550 170) "C")
(command "-HATCH" "S" "L" "" "")
(command "-LAYER" "S" "Textos" "")
(command "-COLOR" "7")
(command "-TEXT" "S" "Standard" "J" "C" (list 4550 130) 10 0 "3xDATO")
(command "-LAYER" "S" "APs" "")
(command "-COLOR" "3")
(command "_.PLINE" (list 4340.0 350) (list 4360.0 350) (list 4350 375) (list 4340.0 350) "")
(command "_.CIRCLE" (list 4350 375) 10)
(command "_.CIRCLE" (list 4350 375) 21.25)
(command "_.CIRCLE" (list 4350 375) 30)
(command "-LAYER" "S" "Textos" "")
(command "-COLOR" "7")
(command "-TEXT" "S" "Standard" "J" "C" (list 4350 330) 10 0 "3xAP")
(command "-LAYER" "S" "Telefonos" "")
(command "-COLOR" "4")
(command "_.PLINE" (list 4440.0 350) (list 4460.0 350) (list 4460.0 380) (list 4440.0 380) "C")
(command "_.CIRCLE" (list 4450 387) 5)
(command "-LAYER" "S" "Textos" "")
(command "-COLOR" "7")
(command "-TEXT" "S" "Standard" "J" "C" (list 4450 330) 10 0 "4xTEL")
(command "-LAYER" "S" "TVs" "")
(command "-COLOR" "5")
(command "_.PLINE" (list 4530.0 350) (list 4570.0 350) (list 4570.0 375) (list 4530.0 375) "C")
(command "_.PLINE" (list 4540.0 350) (list 4560.0 350) (list 4550 340) (list 4540.0 350) "")
(command "-LAYER" "S" "Textos" "")
(command "-COLOR" "7")
(command "-TEXT" "S" "Standard" "J" "C" (list 4550 330) 10 0 "2xTV")
(command "-LAYER" "S" "Camaras" "")
(command "-COLOR" "1")
(command "_.PLINE" (list 4640.0 350) (list 4660.0 350) (list 4660.0 365) (list 4640.0 365) "C")
(command "_.CIRCLE" (list 4650 357.5) 3)
(command "-LAYER" "S" "Textos" "")
(command "-COLOR" "7")
(command "-TEXT" "S" "Standard" "J" "C" (list 4650 330) 10 0 "1xCCTV")
(command "-LAYER" "S" "Datos" "")
(command "-COLOR" "1")
(command "_.PLINE" (list 4740.0 350) (list 4760.0 350) (list 4750 370) "C")
(command "-HATCH" "S" "L" "" "")
(command "-LAYER" "S" "Textos" "")
(command "-COLOR" "7")
(command "-TEXT" "S" "Standard" "J" "C" (list 4750 330) 10 0 "8xDATO")
(command "-LAYER" "S" "APs" "")
(command "-COLOR" "3")
(command "_.PLINE" (list 4340.0 550) (list 4360.0 550) (list 4350 575) (list 4340.0 550) "")
(command "_.CIRCLE" (list 4350 575) 10)
(command "_.CIRCLE" (list 4350 575) 21.25)
(command "_.CIRCLE" (list 4350 575) 30)
(command "-LAYER" "S" "Textos" "")
(command "-COLOR" "7")
(command "-TEXT" "S" "Standard" "J" "C" (list 4350 530) 10 0 "3xAP")
(command "-LAYER" "S" "Telefonos" "")
(command "-COLOR" "4")
(command "_.PLINE" (list 4440.0 550) (list 4460.0 550) (list 4460.0 580) (list 4440.0 580) "C")
(command "_.CIRCLE" (list 4450 587) 5)
(command "-LAYER" "S" "Textos" "")
(command "-COLOR" "7")
(command "-TEXT" "S" "Standard" "J" "C" (list 4450 530) 10 0 "3xTEL")
(command "-LAYER" "S" "TVs" "")
(command "-COLOR" "5")
(command "_.PLINE" (list 4530.0 550) (list 4570.0 550) (list 4570.0 575) (list 4530.0 575) "C")
(command "_.PLINE" (list 4540.0 550) (list 4560.0 550) (list 4550 540) (list 4540.0 550) "")
(command "-LAYER" "S" "Textos" "")
(command "-COLOR" "7")
(command "-TEXT" "S" "Standard" "J" "C" (list 4550 530) 10 0 "1xTV")
(command "-LAYER" "S" "Camaras" "")
(command "-COLOR" "1")
(command "_.PLINE" (list 4640.0 550) (list 4660.0 550) (list 4660.0 565) (list 4640.0 565) "C")
(command "_.CIRCLE" (list 4650 557.5) 3)
(command "-LAYER" "S" "Textos" "")
(command "-COLOR" "7")
(command "-TEXT" "S" "Standard" "J" "C" (list 4650 530) 10 0 "1xCCTV")
(command "-LAYER" "S" "Datos" "")
(command "-COLOR" "1")
(command "_.PLINE" (list 4740.0 550) (list 4760.0 550) (list 4750 570) "C")
(command "-HATCH" "S" "L" "" "")
(command "-LAYER" "S" "Textos" "")
(command "-COLOR" "7")
(command "-TEXT" "S" "Standard" "J" "C" (list 4750 530) 10 0 "7xDATO")
(command "-LAYER" "S" "APs" "")
(command "-COLOR" "3")
(command "_.PLINE" (list 4340.0 750) (list 4360.0 750) (list 4350 775) (list 4340.0 750) "")
(command "_.CIRCLE" (list 4350 775) 10)
(command "_.CIRCLE" (list 4350 775) 21.25)
(command "_.CIRCLE" (list 4350 775) 30)
(command "-LAYER" "S" "Textos" "")
(command "-COLOR" "7")
(command "-TEXT" "S" "Standard" "J" "C" (list 4350 730) 10 0 "3xAP")
(command "-LAYER" "S" "Telefonos" "")
(command "-COLOR" "4")
(command "_.PLINE" (list 4440.0 750) (list 4460.0 750) (list 4460.0 780) (list 4440.0 780) "C")
(command "_.CIRCLE" (list 4450 787) 5)
(command "-LAYER" "S" "Textos" "")
(command "-COLOR" "7")
(command "-TEXT" "S" "Standard" "J" "C" (list 4450 730) 10 0 "3xTEL")
(command "-LAYER" "S" "TVs" "")
(command "-COLOR" "5")
(command "_.PLINE" (list 4530.0 750) (list 4570.0 750) (list 4570.0 775) (list 4530.0 775) "C")
(command "_.PLINE" (list 4540.0 750) (list 4560.0 750) (list 4550 740) (list 4540.0 750) "")
(command "-LAYER" "S" "Textos" "")
(command "-COLOR" "7")
(command "-TEXT" "S" "Standard" "J" "C" (list 4550 730) 10 0 "1xTV")
(command "-LAYER" "S" "Camaras" "")
(command "-COLOR" "1")
(command "_.PLINE" (list 4640.0 750) (list 4660.0 750) (list 4660.0 765) (list 4640.0 765) "C")
(command "_.CIRCLE" (list 4650 757.5) 3)
(command "-LAYER" "S" "Textos" "")
(command "-COLOR" "7")
(command "-TEXT" "S" "Standard" "J" "C" (list 4650 730) 10 0 "1xCCTV")
(command "-LAYER" "S" "Datos" "")
(command "-COLOR" "1")
(command "_.PLINE" (list 4740.0 750) (list 4760.0 750) (list 4750 770) "C")
(command "-HATCH" "S" "L" "" "")
(command "-LAYER" "S" "Textos" "")
(command "-COLOR" "7")
(command "-TEXT" "S" "Standard" "J" "C" (list 4750 730) 10 0 "7xDATO")
(command "-LAYER" "S" "APs" "")
(command "-COLOR" "3")
(command "_.PLINE" (list 4340.0 950) (list 4360.0 950) (list 4350 975) (list 4340.0 950) "")
(command "_.CIRCLE" (list 4350 975) 10)
(command "_.CIRCLE" (list 4350 975) 21.25)
(command "_.CIRCLE" (list 4350 975) 30)
(command "-LAYER" "S" "Textos" "")
(command "-COLOR" "7")
(command "-TEXT" "S" "Standard" "J" "C" (list 4350 930) 10 0 "3xAP")
(command "-LAYER" "S" "Telefonos" "")
(command "-COLOR" "4")
(command "_.PLINE" (list 4440.0 950) (list 4460.0 950) (list 4460.0 980) (list 4440.0 980) "C")
(command "_.CIRCLE" (list 4450 987) 5)
(command "-LAYER" "S" "Textos" "")
(command "-COLOR" "7")
(command "-TEXT" "S" "Standard" "J" "C" (list 4450 930) 10 0 "3xTEL")
(command "-LAYER" "S" "TVs" "")
(command "-COLOR" "5")
(command "_.PLINE" (list 4530.0 950) (list 4570.0 950) (list 4570.0 975) (list 4530.0 975) "C")
(command "_.PLINE" (list 4540.0 950) (list 4560.0 950) (list 4550 940) (list 4540.0 950) "")
(command "-LAYER" "S" "Textos" "")
(command "-COLOR" "7")
(command "-TEXT" "S" "Standard" "J" "C" (list 4550 930) 10 0 "1xTV")
(command "-LAYER" "S" "Camaras" "")
(command "-COLOR" "1")
(command "_.PLINE" (list 4640.0 950) (list 4660.0 950) (list 4660.0 965) (list 4640.0 965) "C")
(command "_.CIRCLE" (list 4650 957.5) 3)
(command "-LAYER" "S" "Textos" "")
(command "-COLOR" "7")
(command "-TEXT" "S" "Standard" "J" "C" (list 4650 930) 10 0 "1xCCTV")
(command "-LAYER" "S" "Datos" "")
(command "-COLOR" "1")
(command "_.PLINE" (list 4740.0 950) (list 4760.0 950) (list 4750 970) "C")
(command "-HATCH" "S" "L" "" "")
(command "-LAYER" "S" "Textos" "")
(command "-COLOR" "7")
(command "-TEXT" "S" "Standard" "J" "C" (list 4750 930) 10 0 "7xDATO")
(command "-LAYER" "S" "APs" "")
(command "-COLOR" "3")
(command "_.PLINE" (list 4340.0 1150) (list 4360.0 1150) (list 4350 1175) (list 4340.0 1150) "")
(command "_.CIRCLE" (list 4350 1175) 10)
(command "_.CIRCLE" (list 4350 1175) 21.25)
(command "_.CIRCLE" (list 4350 1175) 30)
(command "-LAYER" "S" "Textos" "")
(command "-COLOR" "7")
(command "-TEXT" "S" "Standard" "J" "C" (list 4350 1130) 10 0 "3xAP")
(command "-LAYER" "S" "Telefonos" "")
(command "-COLOR" "4")
(command "_.PLINE" (list 4440.0 1150) (list 4460.0 1150) (list 4460.0 1180) (list 4440.0 1180) "C")
(command "_.CIRCLE" (list 4450 1187) 5)
(command "-LAYER" "S" "Textos" "")
(command "-COLOR" "7")
(command "-TEXT" "S" "Standard" "J" "C" (list 4450 1130) 10 0 "3xTEL")
(command "-LAYER" "S" "TVs" "")
(command "-COLOR" "5")
(command "_.PLINE" (list 4530.0 1150) (list 4570.0 1150) (list 4570.0 1175) (list 4530.0 1175) "C")
(command "_.PLINE" (list 4540.0 1150) (list 4560.0 1150) (list 4550 1140) (list 4540.0 1150) "")
(command "-LAYER" "S" "Textos" "")
(command "-COLOR" "7")
(command "-TEXT" "S" "Standard" "J" "C" (list 4550 1130) 10 0 "1xTV")
(command "-LAYER" "S" "Camaras" "")
(command "-COLOR" "1")
(command "_.PLINE" (list 4640.0 1150) (list 4660.0 1150) (list 4660.0 1165) (list 4640.0 1165) "C")
(command "_.CIRCLE" (list 4650 1157.5) 3)
(command "-LAYER" "S" "Textos" "")
(command "-COLOR" "7")
(command "-TEXT" "S" "Standard" "J" "C" (list 4650 1130) 10 0 "1xCCTV")
(command "-LAYER" "S" "Datos" "")
(command "-COLOR" "1")
(command "_.PLINE" (list 4740.0 1150) (list 4760.0 1150) (list 4750 1170) "C")
(command "-HATCH" "S" "L" "" "")
(command "-LAYER" "S" "Textos" "")
(command "-COLOR" "7")
(command "-TEXT" "S" "Standard" "J" "C" (list 4750 1130) 10 0 "7xDATO")
(command "-LAYER" "S" "APs" "")
(command "-COLOR" "3")
(command "_.PLINE" (list 4340.0 1350) (list 4360.0 1350) (list 4350 1375) (list 4340.0 1350) "")
(command "_.CIRCLE" (list 4350 1375) 10)
(command "_.CIRCLE" (list 4350 1375) 21.25)
(command "_.CIRCLE" (list 4350 1375) 30)
(command "-LAYER" "S" "Textos" "")
(command "-COLOR" "7")
(command "-TEXT" "S" "Standard" "J" "C" (list 4350 1330) 10 0 "3xAP")
(command "-LAYER" "S" "Telefonos" "")
(command "-COLOR" "4")
(command "_.PLINE" (list 4440.0 1350) (list 4460.0 1350) (list 4460.0 1380) (list 4440.0 1380) "C")
(command "_.CIRCLE" (list 4450 1387) 5)
(command "-LAYER" "S" "Textos" "")
(command "-COLOR" "7")
(command "-TEXT" "S" "Standard" "J" "C" (list 4450 1330) 10 0 "3xTEL")
(command "-LAYER" "S" "TVs" "")
(command "-COLOR" "5")
(command "_.PLINE" (list 4530.0 1350) (list 4570.0 1350) (list 4570.0 1375) (list 4530.0 1375) "C")
(command "_.PLINE" (list 4540.0 1350) (list 4560.0 1350) (list 4550 1340) (list 4540.0 1350) "")
(command "-LAYER" "S" "Textos" "")
(command "-COLOR" "7")
(command "-TEXT" "S" "Standard" "J" "C" (list 4550 1330) 10 0 "1xTV")
(command "-LAYER" "S" "Camaras" "")
(command "-COLOR" "1")
(command "_.PLINE" (list 4640.0 1350) (list 4660.0 1350) (list 4660.0 1365) (list 4640.0 1365) "C")
(command "_.CIRCLE" (list 4650 1357.5) 3)
(command "-LAYER" "S" "Textos" "")
(command "-COLOR" "7")
(command "-TEXT" "S" "Standard" "J" "C" (list 4650 1330) 10 0 "1xCCTV")
(command "-LAYER" "S" "Datos" "")
(command "-COLOR" "1")
(command "_.PLINE" (list 4740.0 1350) (list 4760.0 1350) (list 4750 1370) "C")
(command "-HATCH" "S" "L" "" "")
(command "-LAYER" "S" "Textos" "")
(command "-COLOR" "7")
(command "-TEXT" "S" "Standard" "J" "C" (list 4750 1330) 10 0 "7xDATO")
(command "-LAYER" "S" "APs" "")
(command "-COLOR" "3")
(command "_.PLINE" (list 4340.0 1550) (list 4360.0 1550) (list 4350 1575) (list 4340.0 1550) "")
(command "_.CIRCLE" (list 4350 1575) 10)
(command "_.CIRCLE" (list 4350 1575) 21.25)
(command "_.CIRCLE" (list 4350 1575) 30)
(command "-LAYER" "S" "Textos" "")
(command "-COLOR" "7")
(command "-TEXT" "S" "Standard" "J" "C" (list 4350 1530) 10 0 "2xAP")
(command "-LAYER" "S" "Telefonos" "")
(command "-COLOR" "4")
(command "_.PLINE" (list 4440.0 1550) (list 4460.0 1550) (list 4460.0 1580) (list 4440.0 1580) "C")
(command "_.CIRCLE" (list 4450 1587) 5)
(command "-LAYER" "S" "Textos" "")
(command "-COLOR" "7")
(command "-TEXT" "S" "Standard" "J" "C" (list 4450 1530) 10 0 "2xTEL")
(command "-LAYER" "S" "TVs" "")
(command "-COLOR" "5")
(command "_.PLINE" (list 4530.0 1550) (list 4570.0 1550) (list 4570.0 1575) (list 4530.0 1575) "C")
(command "_.PLINE" (list 4540.0 1550) (list 4560.0 1550) (list 4550 1540) (list 4540.0 1550) "")
(command "-LAYER" "S" "Textos" "")
(command "-COLOR" "7")
(command "-TEXT" "S" "Standard" "J" "C" (list 4550 1530) 10 0 "1xTV")
(command "-LAYER" "S" "Camaras" "")
(command "-COLOR" "1")
(command "_.PLINE" (list 4640.0 1550) (list 4660.0 1550) (list 4660.0 1565) (list 4640.0 1565) "C")
(command "_.CIRCLE" (list 4650 1557.5) 3)
(command "-LAYER" "S" "Textos" "")
(command "-COLOR" "7")
(command "-TEXT" "S" "Standard" "J" "C" (list 4650 1530) 10 0 "1xCCTV")
(command "-LAYER" "S" "Datos" "")
(command "-COLOR" "1")
(command "_.PLINE" (list 4740.0 1550) (list 4760.0 1550) (list 4750 1570) "C")
(command "-HATCH" "S" "L" "" "")
(command "-LAYER" "S" "Textos" "")
(command "-COLOR" "7")
(command "-TEXT" "S" "Standard" "J" "C" (list 4750 1530) 10 0 "6xDATO")
(princ "DONE.")

; === DIBUJAR TORRE: IDF5 ===
(princ "\n>> Dibujando Torre: IDF5...")
(command "-LAYER" "S" "Textos" "")
(command "-COLOR" "7")
(command "-TEXT" "S" "Standard" "J" "C" (list 5350 150) 25 0 "IDF5")
(princ "\n   - Dibujando switches...")
(command "-LAYER" "S" "Switches" "")
(command "-COLOR" "6")
(command "_.PLINE" (list 5400 -200) (list 5520 -200) (list 5520 -160) (list 5400 -160) "C")
(command "-LAYER" "S" "Textos" "")
(command "-COLOR" "7")
(command "-TEXT" "S" "Standard" "J" "C" (list 5405 -185) 8 0 "SW-CCTV (DS-3E3728F)")
(command "-LAYER" "S" "Switches" "")
(command "-COLOR" "6")
(command "_.PLINE" (list 5400 -140) (list 5520 -140) (list 5520 -100) (list 5400 -100) "C")
(command "-LAYER" "S" "Textos" "")
(command "-COLOR" "7")
(command "-TEXT" "S" "Standard" "J" "C" (list 5405 -125) 8 0 "SW-DATA (Meraki MS225)")
(command "-LAYER" "S" "Switches" "")
(command "-COLOR" "6")
(command "_.PLINE" (list 5400 -80) (list 5520 -80) (list 5520 -40) (list 5400 -40) "C")
(command "-LAYER" "S" "Textos" "")
(command "-COLOR" "7")
(command "-TEXT" "S" "Standard" "J" "C" (list 5405 -65) 8 0 "SW-IPTV (RG-NBS6002)")
(command "-LAYER" "S" "Switches" "")
(command "-COLOR" "6")
(command "_.PLINE" (list 5400 -20) (list 5520 -20) (list 5520 20) (list 5400 20) "C")
(command "-LAYER" "S" "Textos" "")
(command "-COLOR" "7")
(command "-TEXT" "S" "Standard" "J" "C" (list 5405 -5) 8 0 "SW-TEL (Meraki MS225)")
(command "-LAYER" "S" "Switches" "")
(command "-COLOR" "6")
(command "_.PLINE" (list 5400 40) (list 5520 40) (list 5520 80) (list 5400 80) "C")
(command "-LAYER" "S" "Textos" "")
(command "-COLOR" "7")
(command "-TEXT" "S" "Standard" "J" "C" (list 5405 55) 8 0 "SW-WIFI (Meraki MS225)")
(princ "DONE.")
(princ "\n   - Dibujando dispositivos por nivel...")
(command "-LAYER" "S" "APs" "")
(command "-COLOR" "3")
(command "_.PLINE" (list 5390.0 150) (list 5410.0 150) (list 5400 175) (list 5390.0 150) "")
(command "_.CIRCLE" (list 5400 175) 10)
(command "_.CIRCLE" (list 5400 175) 21.25)
(command "_.CIRCLE" (list 5400 175) 30)
(command "-LAYER" "S" "Textos" "")
(command "-COLOR" "7")
(command "-TEXT" "S" "Standard" "J" "C" (list 5400 130) 10 0 "1xAP")
(command "-LAYER" "S" "Telefonos" "")
(command "-COLOR" "4")
(command "_.PLINE" (list 5490.0 150) (list 5510.0 150) (list 5510.0 180) (list 5490.0 180) "C")
(command "_.CIRCLE" (list 5500 187) 5)
(command "-LAYER" "S" "Textos" "")
(command "-COLOR" "7")
(command "-TEXT" "S" "Standard" "J" "C" (list 5500 130) 10 0 "2xTEL")
(command "-LAYER" "S" "TVs" "")
(command "-COLOR" "5")
(command "_.PLINE" (list 5580.0 150) (list 5620.0 150) (list 5620.0 175) (list 5580.0 175) "C")
(command "_.PLINE" (list 5590.0 150) (list 5610.0 150) (list 5600 140) (list 5590.0 150) "")
(command "-LAYER" "S" "Textos" "")
(command "-COLOR" "7")
(command "-TEXT" "S" "Standard" "J" "C" (list 5600 130) 10 0 "1xTV")
(command "-LAYER" "S" "Camaras" "")
(command "-COLOR" "1")
(command "_.PLINE" (list 5690.0 150) (list 5710.0 150) (list 5710.0 165) (list 5690.0 165) "C")
(command "_.CIRCLE" (list 5700 157.5) 3)
(command "-LAYER" "S" "Textos" "")
(command "-COLOR" "7")
(command "-TEXT" "S" "Standard" "J" "C" (list 5700 130) 10 0 "1xCCTV")
(command "-LAYER" "S" "Datos" "")
(command "-COLOR" "1")
(command "_.PLINE" (list 5790.0 150) (list 5810.0 150) (list 5800 170) "C")
(command "-HATCH" "S" "L" "" "")
(command "-LAYER" "S" "Textos" "")
(command "-COLOR" "7")
(command "-TEXT" "S" "Standard" "J" "C" (list 5800 130) 10 0 "5xDATO")
(command "-LAYER" "S" "APs" "")
(command "-COLOR" "3")
(command "_.PLINE" (list 5390.0 350) (list 5410.0 350) (list 5400 375) (list 5390.0 350) "")
(command "_.CIRCLE" (list 5400 375) 10)
(command "_.CIRCLE" (list 5400 375) 21.25)
(command "_.CIRCLE" (list 5400 375) 30)
(command "-LAYER" "S" "Textos" "")
(command "-COLOR" "7")
(command "-TEXT" "S" "Standard" "J" "C" (list 5400 330) 10 0 "4xAP")
(command "-LAYER" "S" "Telefonos" "")
(command "-COLOR" "4")
(command "_.PLINE" (list 5490.0 350) (list 5510.0 350) (list 5510.0 380) (list 5490.0 380) "C")
(command "_.CIRCLE" (list 5500 387) 5)
(command "-LAYER" "S" "Textos" "")
(command "-COLOR" "7")
(command "-TEXT" "S" "Standard" "J" "C" (list 5500 330) 10 0 "5xTEL")
(command "-LAYER" "S" "TVs" "")
(command "-COLOR" "5")
(command "_.PLINE" (list 5580.0 350) (list 5620.0 350) (list 5620.0 375) (list 5580.0 375) "C")
(command "_.PLINE" (list 5590.0 350) (list 5610.0 350) (list 5600 340) (list 5590.0 350) "")
(command "-LAYER" "S" "Textos" "")
(command "-COLOR" "7")
(command "-TEXT" "S" "Standard" "J" "C" (list 5600 330) 10 0 "3xTV")
(command "-LAYER" "S" "Camaras" "")
(command "-COLOR" "1")
(command "_.PLINE" (list 5690.0 350) (list 5710.0 350) (list 5710.0 365) (list 5690.0 365) "C")
(command "_.CIRCLE" (list 5700 357.5) 3)
(command "-LAYER" "S" "Textos" "")
(command "-COLOR" "7")
(command "-TEXT" "S" "Standard" "J" "C" (list 5700 330) 10 0 "2xCCTV")
(command "-LAYER" "S" "Datos" "")
(command "-COLOR" "1")
(command "_.PLINE" (list 5790.0 350) (list 5810.0 350) (list 5800 370) "C")
(command "-HATCH" "S" "L" "" "")
(command "-LAYER" "S" "Textos" "")
(command "-COLOR" "7")
(command "-TEXT" "S" "Standard" "J" "C" (list 5800 330) 10 0 "12xDATO")
(command "-LAYER" "S" "APs" "")
(command "-COLOR" "3")
(command "_.PLINE" (list 5390.0 550) (list 5410.0 550) (list 5400 575) (list 5390.0 550) "")
(command "_.CIRCLE" (list 5400 575) 10)
(command "_.CIRCLE" (list 5400 575) 21.25)
(command "_.CIRCLE" (list 5400 575) 30)
(command "-LAYER" "S" "Textos" "")
(command "-COLOR" "7")
(command "-TEXT" "S" "Standard" "J" "C" (list 5400 530) 10 0 "4xAP")
(command "-LAYER" "S" "Telefonos" "")
(command "-COLOR" "4")
(command "_.PLINE" (list 5490.0 550) (list 5510.0 550) (list 5510.0 580) (list 5490.0 580) "C")
(command "_.CIRCLE" (list 5500 587) 5)
(command "-LAYER" "S" "Textos" "")
(command "-COLOR" "7")
(command "-TEXT" "S" "Standard" "J" "C" (list 5500 530) 10 0 "4xTEL")
(command "-LAYER" "S" "TVs" "")
(command "-COLOR" "5")
(command "_.PLINE" (list 5580.0 550) (list 5620.0 550) (list 5620.0 575) (list 5580.0 575) "C")
(command "_.PLINE" (list 5590.0 550) (list 5610.0 550) (list 5600 540) (list 5590.0 550) "")
(command "-LAYER" "S" "Textos" "")
(command "-COLOR" "7")
(command "-TEXT" "S" "Standard" "J" "C" (list 5600 530) 10 0 "2xTV")
(command "-LAYER" "S" "Camaras" "")
(command "-COLOR" "1")
(command "_.PLINE" (list 5690.0 550) (list 5710.0 550) (list 5710.0 565) (list 5690.0 565) "C")
(command "_.CIRCLE" (list 5700 557.5) 3)
(command "-LAYER" "S" "Textos" "")
(command "-COLOR" "7")
(command "-TEXT" "S" "Standard" "J" "C" (list 5700 530) 10 0 "1xCCTV")
(command "-LAYER" "S" "Datos" "")
(command "-COLOR" "1")
(command "_.PLINE" (list 5790.0 550) (list 5810.0 550) (list 5800 570) "C")
(command "-HATCH" "S" "L" "" "")
(command "-LAYER" "S" "Textos" "")
(command "-COLOR" "7")
(command "-TEXT" "S" "Standard" "J" "C" (list 5800 530) 10 0 "10xDATO")
(command "-LAYER" "S" "APs" "")
(command "-COLOR" "3")
(command "_.PLINE" (list 5390.0 750) (list 5410.0 750) (list 5400 775) (list 5390.0 750) "")
(command "_.CIRCLE" (list 5400 775) 10)
(command "_.CIRCLE" (list 5400 775) 21.25)
(command "_.CIRCLE" (list 5400 775) 30)
(command "-LAYER" "S" "Textos" "")
(command "-COLOR" "7")
(command "-TEXT" "S" "Standard" "J" "C" (list 5400 730) 10 0 "4xAP")
(command "-LAYER" "S" "Telefonos" "")
(command "-COLOR" "4")
(command "_.PLINE" (list 5490.0 750) (list 5510.0 750) (list 5510.0 780) (list 5490.0 780) "C")
(command "_.CIRCLE" (list 5500 787) 5)
(command "-LAYER" "S" "Textos" "")
(command "-COLOR" "7")
(command "-TEXT" "S" "Standard" "J" "C" (list 5500 730) 10 0 "4xTEL")
(command "-LAYER" "S" "TVs" "")
(command "-COLOR" "5")
(command "_.PLINE" (list 5580.0 750) (list 5620.0 750) (list 5620.0 775) (list 5580.0 775) "C")
(command "_.PLINE" (list 5590.0 750) (list 5610.0 750) (list 5600 740) (list 5590.0 750) "")
(command "-LAYER" "S" "Textos" "")
(command "-COLOR" "7")
(command "-TEXT" "S" "Standard" "J" "C" (list 5600 730) 10 0 "2xTV")
(command "-LAYER" "S" "Camaras" "")
(command "-COLOR" "1")
(command "_.PLINE" (list 5690.0 750) (list 5710.0 750) (list 5710.0 765) (list 5690.0 765) "C")
(command "_.CIRCLE" (list 5700 757.5) 3)
(command "-LAYER" "S" "Textos" "")
(command "-COLOR" "7")
(command "-TEXT" "S" "Standard" "J" "C" (list 5700 730) 10 0 "1xCCTV")
(command "-LAYER" "S" "Datos" "")
(command "-COLOR" "1")
(command "_.PLINE" (list 5790.0 750) (list 5810.0 750) (list 5800 770) "C")
(command "-HATCH" "S" "L" "" "")
(command "-LAYER" "S" "Textos" "")
(command "-COLOR" "7")
(command "-TEXT" "S" "Standard" "J" "C" (list 5800 730) 10 0 "10xDATO")
(command "-LAYER" "S" "APs" "")
(command "-COLOR" "3")
(command "_.PLINE" (list 5390.0 950) (list 5410.0 950) (list 5400 975) (list 5390.0 950) "")
(command "_.CIRCLE" (list 5400 975) 10)
(command "_.CIRCLE" (list 5400 975) 21.25)
(command "_.CIRCLE" (list 5400 975) 30)
(command "-LAYER" "S" "Textos" "")
(command "-COLOR" "7")
(command "-TEXT" "S" "Standard" "J" "C" (list 5400 930) 10 0 "4xAP")
(command "-LAYER" "S" "Telefonos" "")
(command "-COLOR" "4")
(command "_.PLINE" (list 5490.0 950) (list 5510.0 950) (list 5510.0 980) (list 5490.0 980) "C")
(command "_.CIRCLE" (list 5500 987) 5)
(command "-LAYER" "S" "Textos" "")
(command "-COLOR" "7")
(command "-TEXT" "S" "Standard" "J" "C" (list 5500 930) 10 0 "4xTEL")
(command "-LAYER" "S" "TVs" "")
(command "-COLOR" "5")
(command "_.PLINE" (list 5580.0 950) (list 5620.0 950) (list 5620.0 975) (list 5580.0 975) "C")
(command "_.PLINE" (list 5590.0 950) (list 5610.0 950) (list 5600 940) (list 5590.0 950) "")
(command "-LAYER" "S" "Textos" "")
(command "-COLOR" "7")
(command "-TEXT" "S" "Standard" "J" "C" (list 5600 930) 10 0 "2xTV")
(command "-LAYER" "S" "Camaras" "")
(command "-COLOR" "1")
(command "_.PLINE" (list 5690.0 950) (list 5710.0 950) (list 5710.0 965) (list 5690.0 965) "C")
(command "_.CIRCLE" (list 5700 957.5) 3)
(command "-LAYER" "S" "Textos" "")
(command "-COLOR" "7")
(command "-TEXT" "S" "Standard" "J" "C" (list 5700 930) 10 0 "1xCCTV")
(command "-LAYER" "S" "Datos" "")
(command "-COLOR" "1")
(command "_.PLINE" (list 5790.0 950) (list 5810.0 950) (list 5800 970) "C")
(command "-HATCH" "S" "L" "" "")
(command "-LAYER" "S" "Textos" "")
(command "-COLOR" "7")
(command "-TEXT" "S" "Standard" "J" "C" (list 5800 930) 10 0 "10xDATO")
(command "-LAYER" "S" "APs" "")
(command "-COLOR" "3")
(command "_.PLINE" (list 5390.0 1150) (list 5410.0 1150) (list 5400 1175) (list 5390.0 1150) "")
(command "_.CIRCLE" (list 5400 1175) 10)
(command "_.CIRCLE" (list 5400 1175) 21.25)
(command "_.CIRCLE" (list 5400 1175) 30)
(command "-LAYER" "S" "Textos" "")
(command "-COLOR" "7")
(command "-TEXT" "S" "Standard" "J" "C" (list 5400 1130) 10 0 "4xAP")
(command "-LAYER" "S" "Telefonos" "")
(command "-COLOR" "4")
(command "_.PLINE" (list 5490.0 1150) (list 5510.0 1150) (list 5510.0 1180) (list 5490.0 1180) "C")
(command "_.CIRCLE" (list 5500 1187) 5)
(command "-LAYER" "S" "Textos" "")
(command "-COLOR" "7")
(command "-TEXT" "S" "Standard" "J" "C" (list 5500 1130) 10 0 "4xTEL")
(command "-LAYER" "S" "TVs" "")
(command "-COLOR" "5")
(command "_.PLINE" (list 5580.0 1150) (list 5620.0 1150) (list 5620.0 1175) (list 5580.0 1175) "C")
(command "_.PLINE" (list 5590.0 1150) (list 5610.0 1150) (list 5600 1140) (list 5590.0 1150) "")
(command "-LAYER" "S" "Textos" "")
(command "-COLOR" "7")
(command "-TEXT" "S" "Standard" "J" "C" (list 5600 1130) 10 0 "2xTV")
(command "-LAYER" "S" "Camaras" "")
(command "-COLOR" "1")
(command "_.PLINE" (list 5690.0 1150) (list 5710.0 1150) (list 5710.0 1165) (list 5690.0 1165) "C")
(command "_.CIRCLE" (list 5700 1157.5) 3)
(command "-LAYER" "S" "Textos" "")
(command "-COLOR" "7")
(command "-TEXT" "S" "Standard" "J" "C" (list 5700 1130) 10 0 "1xCCTV")
(command "-LAYER" "S" "Datos" "")
(command "-COLOR" "1")
(command "_.PLINE" (list 5790.0 1150) (list 5810.0 1150) (list 5800 1170) "C")
(command "-HATCH" "S" "L" "" "")
(command "-LAYER" "S" "Textos" "")
(command "-COLOR" "7")
(command "-TEXT" "S" "Standard" "J" "C" (list 5800 1130) 10 0 "10xDATO")
(command "-LAYER" "S" "APs" "")
(command "-COLOR" "3")
(command "_.PLINE" (list 5390.0 1350) (list 5410.0 1350) (list 5400 1375) (list 5390.0 1350) "")
(command "_.CIRCLE" (list 5400 1375) 10)
(command "_.CIRCLE" (list 5400 1375) 21.25)
(command "_.CIRCLE" (list 5400 1375) 30)
(command "-LAYER" "S" "Textos" "")
(command "-COLOR" "7")
(command "-TEXT" "S" "Standard" "J" "C" (list 5400 1330) 10 0 "4xAP")
(command "-LAYER" "S" "Telefonos" "")
(command "-COLOR" "4")
(command "_.PLINE" (list 5490.0 1350) (list 5510.0 1350) (list 5510.0 1380) (list 5490.0 1380) "C")
(command "_.CIRCLE" (list 5500 1387) 5)
(command "-LAYER" "S" "Textos" "")
(command "-COLOR" "7")
(command "-TEXT" "S" "Standard" "J" "C" (list 5500 1330) 10 0 "4xTEL")
(command "-LAYER" "S" "TVs" "")
(command "-COLOR" "5")
(command "_.PLINE" (list 5580.0 1350) (list 5620.0 1350) (list 5620.0 1375) (list 5580.0 1375) "C")
(command "_.PLINE" (list 5590.0 1350) (list 5610.0 1350) (list 5600 1340) (list 5590.0 1350) "")
(command "-LAYER" "S" "Textos" "")
(command "-COLOR" "7")
(command "-TEXT" "S" "Standard" "J" "C" (list 5600 1330) 10 0 "2xTV")
(command "-LAYER" "S" "Camaras" "")
(command "-COLOR" "1")
(command "_.PLINE" (list 5690.0 1350) (list 5710.0 1350) (list 5710.0 1365) (list 5690.0 1365) "C")
(command "_.CIRCLE" (list 5700 1357.5) 3)
(command "-LAYER" "S" "Textos" "")
(command "-COLOR" "7")
(command "-TEXT" "S" "Standard" "J" "C" (list 5700 1330) 10 0 "1xCCTV")
(command "-LAYER" "S" "Datos" "")
(command "-COLOR" "1")
(command "_.PLINE" (list 5790.0 1350) (list 5810.0 1350) (list 5800 1370) "C")
(command "-HATCH" "S" "L" "" "")
(command "-LAYER" "S" "Textos" "")
(command "-COLOR" "7")
(command "-TEXT" "S" "Standard" "J" "C" (list 5800 1330) 10 0 "10xDATO")
(command "-LAYER" "S" "APs" "")
(command "-COLOR" "3")
(command "_.PLINE" (list 5390.0 1550) (list 5410.0 1550) (list 5400 1575) (list 5390.0 1550) "")
(command "_.CIRCLE" (list 5400 1575) 10)
(command "_.CIRCLE" (list 5400 1575) 21.25)
(command "_.CIRCLE" (list 5400 1575) 30)
(command "-LAYER" "S" "Textos" "")
(command "-COLOR" "7")
(command "-TEXT" "S" "Standard" "J" "C" (list 5400 1530) 10 0 "2xAP")
(command "-LAYER" "S" "Telefonos" "")
(command "-COLOR" "4")
(command "_.PLINE" (list 5490.0 1550) (list 5510.0 1550) (list 5510.0 1580) (list 5490.0 1580) "C")
(command "_.CIRCLE" (list 5500 1587) 5)
(command "-LAYER" "S" "Textos" "")
(command "-COLOR" "7")
(command "-TEXT" "S" "Standard" "J" "C" (list 5500 1530) 10 0 "2xTEL")
(command "-LAYER" "S" "TVs" "")
(command "-COLOR" "5")
(command "_.PLINE" (list 5580.0 1550) (list 5620.0 1550) (list 5620.0 1575) (list 5580.0 1575) "C")
(command "_.PLINE" (list 5590.0 1550) (list 5610.0 1550) (list 5600 1540) (list 5590.0 1550) "")
(command "-LAYER" "S" "Textos" "")
(command "-COLOR" "7")
(command "-TEXT" "S" "Standard" "J" "C" (list 5600 1530) 10 0 "1xTV")
(command "-LAYER" "S" "Camaras" "")
(command "-COLOR" "1")
(command "_.PLINE" (list 5690.0 1550) (list 5710.0 1550) (list 5710.0 1565) (list 5690.0 1565) "C")
(command "_.CIRCLE" (list 5700 1557.5) 3)
(command "-LAYER" "S" "Textos" "")
(command "-COLOR" "7")
(command "-TEXT" "S" "Standard" "J" "C" (list 5700 1530) 10 0 "1xCCTV")
(command "-LAYER" "S" "Datos" "")
(command "-COLOR" "1")
(command "_.PLINE" (list 5790.0 1550) (list 5810.0 1550) (list 5800 1570) "C")
(command "-HATCH" "S" "L" "" "")
(command "-LAYER" "S" "Textos" "")
(command "-COLOR" "7")
(command "-TEXT" "S" "Standard" "J" "C" (list 5800 1530) 10 0 "6xDATO")
(princ "DONE.")

; === DIBUJAR TORRE: IDF6 ===
(princ "\n>> Dibujando Torre: IDF6...")
(command "-LAYER" "S" "Textos" "")
(command "-COLOR" "7")
(command "-TEXT" "S" "Standard" "J" "C" (list 6400 150) 25 0 "IDF6")
(princ "\n   - Dibujando switches...")
(command "-LAYER" "S" "Switches" "")
(command "-COLOR" "6")
(command "_.PLINE" (list 6450 -200) (list 6570 -200) (list 6570 -160) (list 6450 -160) "C")
(command "-LAYER" "S" "Textos" "")
(command "-COLOR" "7")
(command "-TEXT" "S" "Standard" "J" "C" (list 6455 -185) 8 0 "SW-CCTV (DS-3E3728F)")
(command "-LAYER" "S" "Switches" "")
(command "-COLOR" "6")
(command "_.PLINE" (list 6450 -140) (list 6570 -140) (list 6570 -100) (list 6450 -100) "C")
(command "-LAYER" "S" "Textos" "")
(command "-COLOR" "7")
(command "-TEXT" "S" "Standard" "J" "C" (list 6455 -125) 8 0 "SW-DATA (Meraki MS225)")
(command "-LAYER" "S" "Switches" "")
(command "-COLOR" "6")
(command "_.PLINE" (list 6450 -80) (list 6570 -80) (list 6570 -40) (list 6450 -40) "C")
(command "-LAYER" "S" "Textos" "")
(command "-COLOR" "7")
(command "-TEXT" "S" "Standard" "J" "C" (list 6455 -65) 8 0 "SW-IPTV (RG-NBS6002)")
(command "-LAYER" "S" "Switches" "")
(command "-COLOR" "6")
(command "_.PLINE" (list 6450 -20) (list 6570 -20) (list 6570 20) (list 6450 20) "C")
(command "-LAYER" "S" "Textos" "")
(command "-COLOR" "7")
(command "-TEXT" "S" "Standard" "J" "C" (list 6455 -5) 8 0 "SW-TEL (Meraki MS225)")
(command "-LAYER" "S" "Switches" "")
(command "-COLOR" "6")
(command "_.PLINE" (list 6450 40) (list 6570 40) (list 6570 80) (list 6450 80) "C")
(command "-LAYER" "S" "Textos" "")
(command "-COLOR" "7")
(command "-TEXT" "S" "Standard" "J" "C" (list 6455 55) 8 0 "SW-WIFI (Meraki MS225)")
(princ "DONE.")
(princ "\n   - Dibujando dispositivos por nivel...")
(command "-LAYER" "S" "APs" "")
(command "-COLOR" "3")
(command "_.PLINE" (list 6440.0 150) (list 6460.0 150) (list 6450 175) (list 6440.0 150) "")
(command "_.CIRCLE" (list 6450 175) 10)
(command "_.CIRCLE" (list 6450 175) 21.25)
(command "_.CIRCLE" (list 6450 175) 30)
(command "-LAYER" "S" "Textos" "")
(command "-COLOR" "7")
(command "-TEXT" "S" "Standard" "J" "C" (list 6450 130) 10 0 "2xAP")
(command "-LAYER" "S" "Telefonos" "")
(command "-COLOR" "4")
(command "_.PLINE" (list 6540.0 150) (list 6560.0 150) (list 6560.0 180) (list 6540.0 180) "C")
(command "_.CIRCLE" (list 6550 187) 5)
(command "-LAYER" "S" "Textos" "")
(command "-COLOR" "7")
(command "-TEXT" "S" "Standard" "J" "C" (list 6550 130) 10 0 "3xTEL")
(command "-LAYER" "S" "TVs" "")
(command "-COLOR" "5")
(command "_.PLINE" (list 6630.0 150) (list 6670.0 150) (list 6670.0 175) (list 6630.0 175) "C")
(command "_.PLINE" (list 6640.0 150) (list 6660.0 150) (list 6650 140) (list 6640.0 150) "")
(command "-LAYER" "S" "Textos" "")
(command "-COLOR" "7")
(command "-TEXT" "S" "Standard" "J" "C" (list 6650 130) 10 0 "2xTV")
(command "-LAYER" "S" "Camaras" "")
(command "-COLOR" "1")
(command "_.PLINE" (list 6740.0 150) (list 6760.0 150) (list 6760.0 165) (list 6740.0 165) "C")
(command "_.CIRCLE" (list 6750 157.5) 3)
(command "-LAYER" "S" "Textos" "")
(command "-COLOR" "7")
(command "-TEXT" "S" "Standard" "J" "C" (list 6750 130) 10 0 "1xCCTV")
(command "-LAYER" "S" "Datos" "")
(command "-COLOR" "1")
(command "_.PLINE" (list 6840.0 150) (list 6860.0 150) (list 6850 170) "C")
(command "-HATCH" "S" "L" "" "")
(command "-LAYER" "S" "Textos" "")
(command "-COLOR" "7")
(command "-TEXT" "S" "Standard" "J" "C" (list 6850 130) 10 0 "7xDATO")
(command "-LAYER" "S" "APs" "")
(command "-COLOR" "3")
(command "_.PLINE" (list 6440.0 350) (list 6460.0 350) (list 6450 375) (list 6440.0 350) "")
(command "_.CIRCLE" (list 6450 375) 10)
(command "_.CIRCLE" (list 6450 375) 21.25)
(command "_.CIRCLE" (list 6450 375) 30)
(command "-LAYER" "S" "Textos" "")
(command "-COLOR" "7")
(command "-TEXT" "S" "Standard" "J" "C" (list 6450 330) 10 0 "5xAP")
(command "-LAYER" "S" "Telefonos" "")
(command "-COLOR" "4")
(command "_.PLINE" (list 6540.0 350) (list 6560.0 350) (list 6560.0 380) (list 6540.0 380) "C")
(command "_.CIRCLE" (list 6550 387) 5)
(command "-LAYER" "S" "Textos" "")
(command "-COLOR" "7")
(command "-TEXT" "S" "Standard" "J" "C" (list 6550 330) 10 0 "6xTEL")
(command "-LAYER" "S" "TVs" "")
(command "-COLOR" "5")
(command "_.PLINE" (list 6630.0 350) (list 6670.0 350) (list 6670.0 375) (list 6630.0 375) "C")
(command "_.PLINE" (list 6640.0 350) (list 6660.0 350) (list 6650 340) (list 6640.0 350) "")
(command "-LAYER" "S" "Textos" "")
(command "-COLOR" "7")
(command "-TEXT" "S" "Standard" "J" "C" (list 6650 330) 10 0 "4xTV")
(command "-LAYER" "S" "Camaras" "")
(command "-COLOR" "1")
(command "_.PLINE" (list 6740.0 350) (list 6760.0 350) (list 6760.0 365) (list 6740.0 365) "C")
(command "_.CIRCLE" (list 6750 357.5) 3)
(command "-LAYER" "S" "Textos" "")
(command "-COLOR" "7")
(command "-TEXT" "S" "Standard" "J" "C" (list 6750 330) 10 0 "2xCCTV")
(command "-LAYER" "S" "Datos" "")
(command "-COLOR" "1")
(command "_.PLINE" (list 6840.0 350) (list 6860.0 350) (list 6850 370) "C")
(command "-HATCH" "S" "L" "" "")
(command "-LAYER" "S" "Textos" "")
(command "-COLOR" "7")
(command "-TEXT" "S" "Standard" "J" "C" (list 6850 330) 10 0 "14xDATO")
(command "-LAYER" "S" "APs" "")
(command "-COLOR" "3")
(command "_.PLINE" (list 6440.0 550) (list 6460.0 550) (list 6450 575) (list 6440.0 550) "")
(command "_.CIRCLE" (list 6450 575) 10)
(command "_.CIRCLE" (list 6450 575) 21.25)
(command "_.CIRCLE" (list 6450 575) 30)
(command "-LAYER" "S" "Textos" "")
(command "-COLOR" "7")
(command "-TEXT" "S" "Standard" "J" "C" (list 6450 530) 10 0 "4xAP")
(command "-LAYER" "S" "Telefonos" "")
(command "-COLOR" "4")
(command "_.PLINE" (list 6540.0 550) (list 6560.0 550) (list 6560.0 580) (list 6540.0 580) "C")
(command "_.CIRCLE" (list 6550 587) 5)
(command "-LAYER" "S" "Textos" "")
(command "-COLOR" "7")
(command "-TEXT" "S" "Standard" "J" "C" (list 6550 530) 10 0 "4xTEL")
(command "-LAYER" "S" "TVs" "")
(command "-COLOR" "5")
(command "_.PLINE" (list 6630.0 550) (list 6670.0 550) (list 6670.0 575) (list 6630.0 575) "C")
(command "_.PLINE" (list 6640.0 550) (list 6660.0 550) (list 6650 540) (list 6640.0 550) "")
(command "-LAYER" "S" "Textos" "")
(command "-COLOR" "7")
(command "-TEXT" "S" "Standard" "J" "C" (list 6650 530) 10 0 "2xTV")
(command "-LAYER" "S" "Camaras" "")
(command "-COLOR" "1")
(command "_.PLINE" (list 6740.0 550) (list 6760.0 550) (list 6760.0 565) (list 6740.0 565) "C")
(command "_.CIRCLE" (list 6750 557.5) 3)
(command "-LAYER" "S" "Textos" "")
(command "-COLOR" "7")
(command "-TEXT" "S" "Standard" "J" "C" (list 6750 530) 10 0 "1xCCTV")
(command "-LAYER" "S" "Datos" "")
(command "-COLOR" "1")
(command "_.PLINE" (list 6840.0 550) (list 6860.0 550) (list 6850 570) "C")
(command "-HATCH" "S" "L" "" "")
(command "-LAYER" "S" "Textos" "")
(command "-COLOR" "7")
(command "-TEXT" "S" "Standard" "J" "C" (list 6850 530) 10 0 "10xDATO")
(command "-LAYER" "S" "APs" "")
(command "-COLOR" "3")
(command "_.PLINE" (list 6440.0 750) (list 6460.0 750) (list 6450 775) (list 6440.0 750) "")
(command "_.CIRCLE" (list 6450 775) 10)
(command "_.CIRCLE" (list 6450 775) 21.25)
(command "_.CIRCLE" (list 6450 775) 30)
(command "-LAYER" "S" "Textos" "")
(command "-COLOR" "7")
(command "-TEXT" "S" "Standard" "J" "C" (list 6450 730) 10 0 "4xAP")
(command "-LAYER" "S" "Telefonos" "")
(command "-COLOR" "4")
(command "_.PLINE" (list 6540.0 750) (list 6560.0 750) (list 6560.0 780) (list 6540.0 780) "C")
(command "_.CIRCLE" (list 6550 787) 5)
(command "-LAYER" "S" "Textos" "")
(command "-COLOR" "7")
(command "-TEXT" "S" "Standard" "J" "C" (list 6550 730) 10 0 "4xTEL")
(command "-LAYER" "S" "TVs" "")
(command "-COLOR" "5")
(command "_.PLINE" (list 6630.0 750) (list 6670.0 750) (list 6670.0 775) (list 6630.0 775) "C")
(command "_.PLINE" (list 6640.0 750) (list 6660.0 750) (list 6650 740) (list 6640.0 750) "")
(command "-LAYER" "S" "Textos" "")
(command "-COLOR" "7")
(command "-TEXT" "S" "Standard" "J" "C" (list 6650 730) 10 0 "2xTV")
(command "-LAYER" "S" "Camaras" "")
(command "-COLOR" "1")
(command "_.PLINE" (list 6740.0 750) (list 6760.0 750) (list 6760.0 765) (list 6740.0 765) "C")
(command "_.CIRCLE" (list 6750 757.5) 3)
(command "-LAYER" "S" "Textos" "")
(command "-COLOR" "7")
(command "-TEXT" "S" "Standard" "J" "C" (list 6750 730) 10 0 "1xCCTV")
(command "-LAYER" "S" "Datos" "")
(command "-COLOR" "1")
(command "_.PLINE" (list 6840.0 750) (list 6860.0 750) (list 6850 770) "C")
(command "-HATCH" "S" "L" "" "")
(command "-LAYER" "S" "Textos" "")
(command "-COLOR" "7")
(command "-TEXT" "S" "Standard" "J" "C" (list 6850 730) 10 0 "10xDATO")
(command "-LAYER" "S" "APs" "")
(command "-COLOR" "3")
(command "_.PLINE" (list 6440.0 950) (list 6460.0 950) (list 6450 975) (list 6440.0 950) "")
(command "_.CIRCLE" (list 6450 975) 10)
(command "_.CIRCLE" (list 6450 975) 21.25)
(command "_.CIRCLE" (list 6450 975) 30)
(command "-LAYER" "S" "Textos" "")
(command "-COLOR" "7")
(command "-TEXT" "S" "Standard" "J" "C" (list 6450 930) 10 0 "4xAP")
(command "-LAYER" "S" "Telefonos" "")
(command "-COLOR" "4")
(command "_.PLINE" (list 6540.0 950) (list 6560.0 950) (list 6560.0 980) (list 6540.0 980) "C")
(command "_.CIRCLE" (list 6550 987) 5)
(command "-LAYER" "S" "Textos" "")
(command "-COLOR" "7")
(command "-TEXT" "S" "Standard" "J" "C" (list 6550 930) 10 0 "4xTEL")
(command "-LAYER" "S" "TVs" "")
(command "-COLOR" "5")
(command "_.PLINE" (list 6630.0 950) (list 6670.0 950) (list 6670.0 975) (list 6630.0 975) "C")
(command "_.PLINE" (list 6640.0 950) (list 6660.0 950) (list 6650 940) (list 6640.0 950) "")
(command "-LAYER" "S" "Textos" "")
(command "-COLOR" "7")
(command "-TEXT" "S" "Standard" "J" "C" (list 6650 930) 10 0 "2xTV")
(command "-LAYER" "S" "Camaras" "")
(command "-COLOR" "1")
(command "_.PLINE" (list 6740.0 950) (list 6760.0 950) (list 6760.0 965) (list 6740.0 965) "C")
(command "_.CIRCLE" (list 6750 957.5) 3)
(command "-LAYER" "S" "Textos" "")
(command "-COLOR" "7")
(command "-TEXT" "S" "Standard" "J" "C" (list 6750 930) 10 0 "1xCCTV")
(command "-LAYER" "S" "Datos" "")
(command "-COLOR" "1")
(command "_.PLINE" (list 6840.0 950) (list 6860.0 950) (list 6850 970) "C")
(command "-HATCH" "S" "L" "" "")
(command "-LAYER" "S" "Textos" "")
(command "-COLOR" "7")
(command "-TEXT" "S" "Standard" "J" "C" (list 6850 930) 10 0 "10xDATO")
(command "-LAYER" "S" "APs" "")
(command "-COLOR" "3")
(command "_.PLINE" (list 6440.0 1150) (list 6460.0 1150) (list 6450 1175) (list 6440.0 1150) "")
(command "_.CIRCLE" (list 6450 1175) 10)
(command "_.CIRCLE" (list 6450 1175) 21.25)
(command "_.CIRCLE" (list 6450 1175) 30)
(command "-LAYER" "S" "Textos" "")
(command "-COLOR" "7")
(command "-TEXT" "S" "Standard" "J" "C" (list 6450 1130) 10 0 "4xAP")
(command "-LAYER" "S" "Telefonos" "")
(command "-COLOR" "4")
(command "_.PLINE" (list 6540.0 1150) (list 6560.0 1150) (list 6560.0 1180) (list 6540.0 1180) "C")
(command "_.CIRCLE" (list 6550 1187) 5)
(command "-LAYER" "S" "Textos" "")
(command "-COLOR" "7")
(command "-TEXT" "S" "Standard" "J" "C" (list 6550 1130) 10 0 "4xTEL")
(command "-LAYER" "S" "TVs" "")
(command "-COLOR" "5")
(command "_.PLINE" (list 6630.0 1150) (list 6670.0 1150) (list 6670.0 1175) (list 6630.0 1175) "C")
(command "_.PLINE" (list 6640.0 1150) (list 6660.0 1150) (list 6650 1140) (list 6640.0 1150) "")
(command "-LAYER" "S" "Textos" "")
(command "-COLOR" "7")
(command "-TEXT" "S" "Standard" "J" "C" (list 6650 1130) 10 0 "2xTV")
(command "-LAYER" "S" "Camaras" "")
(command "-COLOR" "1")
(command "_.PLINE" (list 6740.0 1150) (list 6760.0 1150) (list 6760.0 1165) (list 6740.0 1165) "C")
(command "_.CIRCLE" (list 6750 1157.5) 3)
(command "-LAYER" "S" "Textos" "")
(command "-COLOR" "7")
(command "-TEXT" "S" "Standard" "J" "C" (list 6750 1130) 10 0 "1xCCTV")
(command "-LAYER" "S" "Datos" "")
(command "-COLOR" "1")
(command "_.PLINE" (list 6840.0 1150) (list 6860.0 1150) (list 6850 1170) "C")
(command "-HATCH" "S" "L" "" "")
(command "-LAYER" "S" "Textos" "")
(command "-COLOR" "7")
(command "-TEXT" "S" "Standard" "J" "C" (list 6850 1130) 10 0 "10xDATO")
(command "-LAYER" "S" "APs" "")
(command "-COLOR" "3")
(command "_.PLINE" (list 6440.0 1350) (list 6460.0 1350) (list 6450 1375) (list 6440.0 1350) "")
(command "_.CIRCLE" (list 6450 1375) 10)
(command "_.CIRCLE" (list 6450 1375) 21.25)
(command "_.CIRCLE" (list 6450 1375) 30)
(command "-LAYER" "S" "Textos" "")
(command "-COLOR" "7")
(command "-TEXT" "S" "Standard" "J" "C" (list 6450 1330) 10 0 "4xAP")
(command "-LAYER" "S" "Telefonos" "")
(command "-COLOR" "4")
(command "_.PLINE" (list 6540.0 1350) (list 6560.0 1350) (list 6560.0 1380) (list 6540.0 1380) "C")
(command "_.CIRCLE" (list 6550 1387) 5)
(command "-LAYER" "S" "Textos" "")
(command "-COLOR" "7")
(command "-TEXT" "S" "Standard" "J" "C" (list 6550 1330) 10 0 "4xTEL")
(command "-LAYER" "S" "TVs" "")
(command "-COLOR" "5")
(command "_.PLINE" (list 6630.0 1350) (list 6670.0 1350) (list 6670.0 1375) (list 6630.0 1375) "C")
(command "_.PLINE" (list 6640.0 1350) (list 6660.0 1350) (list 6650 1340) (list 6640.0 1350) "")
(command "-LAYER" "S" "Textos" "")
(command "-COLOR" "7")
(command "-TEXT" "S" "Standard" "J" "C" (list 6650 1330) 10 0 "2xTV")
(command "-LAYER" "S" "Camaras" "")
(command "-COLOR" "1")
(command "_.PLINE" (list 6740.0 1350) (list 6760.0 1350) (list 6760.0 1365) (list 6740.0 1365) "C")
(command "_.CIRCLE" (list 6750 1357.5) 3)
(command "-LAYER" "S" "Textos" "")
(command "-COLOR" "7")
(command "-TEXT" "S" "Standard" "J" "C" (list 6750 1330) 10 0 "1xCCTV")
(command "-LAYER" "S" "Datos" "")
(command "-COLOR" "1")
(command "_.PLINE" (list 6840.0 1350) (list 6860.0 1350) (list 6850 1370) "C")
(command "-HATCH" "S" "L" "" "")
(command "-LAYER" "S" "Textos" "")
(command "-COLOR" "7")
(command "-TEXT" "S" "Standard" "J" "C" (list 6850 1330) 10 0 "10xDATO")
(command "-LAYER" "S" "APs" "")
(command "-COLOR" "3")
(command "_.PLINE" (list 6440.0 1550) (list 6460.0 1550) (list 6450 1575) (list 6440.0 1550) "")
(command "_.CIRCLE" (list 6450 1575) 10)
(command "_.CIRCLE" (list 6450 1575) 21.25)
(command "_.CIRCLE" (list 6450 1575) 30)
(command "-LAYER" "S" "Textos" "")
(command "-COLOR" "7")
(command "-TEXT" "S" "Standard" "J" "C" (list 6450 1530) 10 0 "2xAP")
(command "-LAYER" "S" "Telefonos" "")
(command "-COLOR" "4")
(command "_.PLINE" (list 6540.0 1550) (list 6560.0 1550) (list 6560.0 1580) (list 6540.0 1580) "C")
(command "_.CIRCLE" (list 6550 1587) 5)
(command "-LAYER" "S" "Textos" "")
(command "-COLOR" "7")
(command "-TEXT" "S" "Standard" "J" "C" (list 6550 1530) 10 0 "2xTEL")
(command "-LAYER" "S" "TVs" "")
(command "-COLOR" "5")
(command "_.PLINE" (list 6630.0 1550) (list 6670.0 1550) (list 6670.0 1575) (list 6630.0 1575) "C")
(command "_.PLINE" (list 6640.0 1550) (list 6660.0 1550) (list 6650 1540) (list 6640.0 1550) "")
(command "-LAYER" "S" "Textos" "")
(command "-COLOR" "7")
(command "-TEXT" "S" "Standard" "J" "C" (list 6650 1530) 10 0 "1xTV")
(command "-LAYER" "S" "Camaras" "")
(command "-COLOR" "1")
(command "_.PLINE" (list 6740.0 1550) (list 6760.0 1550) (list 6760.0 1565) (list 6740.0 1565) "C")
(command "_.CIRCLE" (list 6750 1557.5) 3)
(command "-LAYER" "S" "Textos" "")
(command "-COLOR" "7")
(command "-TEXT" "S" "Standard" "J" "C" (list 6750 1530) 10 0 "1xCCTV")
(command "-LAYER" "S" "Datos" "")
(command "-COLOR" "1")
(command "_.PLINE" (list 6840.0 1550) (list 6860.0 1550) (list 6850 1570) "C")
(command "-HATCH" "S" "L" "" "")
(command "-LAYER" "S" "Textos" "")
(command "-COLOR" "7")
(command "-TEXT" "S" "Standard" "J" "C" (list 6850 1530) 10 0 "6xDATO")
(princ "DONE.")

; === DIBUJAR TORRE: IDF7 ===
(princ "\n>> Dibujando Torre: IDF7...")
(command "-LAYER" "S" "Textos" "")
(command "-COLOR" "7")
(command "-TEXT" "S" "Standard" "J" "C" (list 7450 150) 25 0 "IDF7")
(princ "\n   - Dibujando switches...")
(command "-LAYER" "S" "Switches" "")
(command "-COLOR" "6")
(command "_.PLINE" (list 7500 -200) (list 7620 -200) (list 7620 -160) (list 7500 -160) "C")
(command "-LAYER" "S" "Textos" "")
(command "-COLOR" "7")
(command "-TEXT" "S" "Standard" "J" "C" (list 7505 -185) 8 0 "SW-CCTV (DS-3E3728F)")
(command "-LAYER" "S" "Switches" "")
(command "-COLOR" "6")
(command "_.PLINE" (list 7500 -140) (list 7620 -140) (list 7620 -100) (list 7500 -100) "C")
(command "-LAYER" "S" "Textos" "")
(command "-COLOR" "7")
(command "-TEXT" "S" "Standard" "J" "C" (list 7505 -125) 8 0 "SW-DATA (Meraki MS225)")
(command "-LAYER" "S" "Switches" "")
(command "-COLOR" "6")
(command "_.PLINE" (list 7500 -80) (list 7620 -80) (list 7620 -40) (list 7500 -40) "C")
(command "-LAYER" "S" "Textos" "")
(command "-COLOR" "7")
(command "-TEXT" "S" "Standard" "J" "C" (list 7505 -65) 8 0 "SW-IPTV (RG-NBS6002)")
(command "-LAYER" "S" "Switches" "")
(command "-COLOR" "6")
(command "_.PLINE" (list 7500 -20) (list 7620 -20) (list 7620 20) (list 7500 20) "C")
(command "-LAYER" "S" "Textos" "")
(command "-COLOR" "7")
(command "-TEXT" "S" "Standard" "J" "C" (list 7505 -5) 8 0 "SW-TEL (Meraki MS225)")
(command "-LAYER" "S" "Switches" "")
(command "-COLOR" "6")
(command "_.PLINE" (list 7500 40) (list 7620 40) (list 7620 80) (list 7500 80) "C")
(command "-LAYER" "S" "Textos" "")
(command "-COLOR" "7")
(command "-TEXT" "S" "Standard" "J" "C" (list 7505 55) 8 0 "SW-WIFI (Meraki MS225)")
(princ "DONE.")
(princ "\n   - Dibujando dispositivos por nivel...")
(command "-LAYER" "S" "APs" "")
(command "-COLOR" "3")
(command "_.PLINE" (list 7490.0 150) (list 7510.0 150) (list 7500 175) (list 7490.0 150) "")
(command "_.CIRCLE" (list 7500 175) 10)
(command "_.CIRCLE" (list 7500 175) 21.25)
(command "_.CIRCLE" (list 7500 175) 30)
(command "-LAYER" "S" "Textos" "")
(command "-COLOR" "7")
(command "-TEXT" "S" "Standard" "J" "C" (list 7500 130) 10 0 "2xAP")
(command "-LAYER" "S" "Telefonos" "")
(command "-COLOR" "4")
(command "_.PLINE" (list 7590.0 150) (list 7610.0 150) (list 7610.0 180) (list 7590.0 180) "C")
(command "_.CIRCLE" (list 7600 187) 5)
(command "-LAYER" "S" "Textos" "")
(command "-COLOR" "7")
(command "-TEXT" "S" "Standard" "J" "C" (list 7600 130) 10 0 "3xTEL")
(command "-LAYER" "S" "TVs" "")
(command "-COLOR" "5")
(command "_.PLINE" (list 7680.0 150) (list 7720.0 150) (list 7720.0 175) (list 7680.0 175) "C")
(command "_.PLINE" (list 7690.0 150) (list 7710.0 150) (list 7700 140) (list 7690.0 150) "")
(command "-LAYER" "S" "Textos" "")
(command "-COLOR" "7")
(command "-TEXT" "S" "Standard" "J" "C" (list 7700 130) 10 0 "2xTV")
(command "-LAYER" "S" "Camaras" "")
(command "-COLOR" "1")
(command "_.PLINE" (list 7790.0 150) (list 7810.0 150) (list 7810.0 165) (list 7790.0 165) "C")
(command "_.CIRCLE" (list 7800 157.5) 3)
(command "-LAYER" "S" "Textos" "")
(command "-COLOR" "7")
(command "-TEXT" "S" "Standard" "J" "C" (list 7800 130) 10 0 "1xCCTV")
(command "-LAYER" "S" "Datos" "")
(command "-COLOR" "1")
(command "_.PLINE" (list 7890.0 150) (list 7910.0 150) (list 7900 170) "C")
(command "-HATCH" "S" "L" "" "")
(command "-LAYER" "S" "Textos" "")
(command "-COLOR" "7")
(command "-TEXT" "S" "Standard" "J" "C" (list 7900 130) 10 0 "7xDATO")
(command "-LAYER" "S" "APs" "")
(command "-COLOR" "3")
(command "_.PLINE" (list 7490.0 350) (list 7510.0 350) (list 7500 375) (list 7490.0 350) "")
(command "_.CIRCLE" (list 7500 375) 10)
(command "_.CIRCLE" (list 7500 375) 21.25)
(command "_.CIRCLE" (list 7500 375) 30)
(command "-LAYER" "S" "Textos" "")
(command "-COLOR" "7")
(command "-TEXT" "S" "Standard" "J" "C" (list 7500 330) 10 0 "5xAP")
(command "-LAYER" "S" "Telefonos" "")
(command "-COLOR" "4")
(command "_.PLINE" (list 7590.0 350) (list 7610.0 350) (list 7610.0 380) (list 7590.0 380) "C")
(command "_.CIRCLE" (list 7600 387) 5)
(command "-LAYER" "S" "Textos" "")
(command "-COLOR" "7")
(command "-TEXT" "S" "Standard" "J" "C" (list 7600 330) 10 0 "6xTEL")
(command "-LAYER" "S" "TVs" "")
(command "-COLOR" "5")
(command "_.PLINE" (list 7680.0 350) (list 7720.0 350) (list 7720.0 375) (list 7680.0 375) "C")
(command "_.PLINE" (list 7690.0 350) (list 7710.0 350) (list 7700 340) (list 7690.0 350) "")
(command "-LAYER" "S" "Textos" "")
(command "-COLOR" "7")
(command "-TEXT" "S" "Standard" "J" "C" (list 7700 330) 10 0 "4xTV")
(command "-LAYER" "S" "Camaras" "")
(command "-COLOR" "1")
(command "_.PLINE" (list 7790.0 350) (list 7810.0 350) (list 7810.0 365) (list 7790.0 365) "C")
(command "_.CIRCLE" (list 7800 357.5) 3)
(command "-LAYER" "S" "Textos" "")
(command "-COLOR" "7")
(command "-TEXT" "S" "Standard" "J" "C" (list 7800 330) 10 0 "2xCCTV")
(command "-LAYER" "S" "Datos" "")
(command "-COLOR" "1")
(command "_.PLINE" (list 7890.0 350) (list 7910.0 350) (list 7900 370) "C")
(command "-HATCH" "S" "L" "" "")
(command "-LAYER" "S" "Textos" "")
(command "-COLOR" "7")
(command "-TEXT" "S" "Standard" "J" "C" (list 7900 330) 10 0 "14xDATO")
(command "-LAYER" "S" "APs" "")
(command "-COLOR" "3")
(command "_.PLINE" (list 7490.0 550) (list 7510.0 550) (list 7500 575) (list 7490.0 550) "")
(command "_.CIRCLE" (list 7500 575) 10)
(command "_.CIRCLE" (list 7500 575) 21.25)
(command "_.CIRCLE" (list 7500 575) 30)
(command "-LAYER" "S" "Textos" "")
(command "-COLOR" "7")
(command "-TEXT" "S" "Standard" "J" "C" (list 7500 530) 10 0 "4xAP")
(command "-LAYER" "S" "Telefonos" "")
(command "-COLOR" "4")
(command "_.PLINE" (list 7590.0 550) (list 7610.0 550) (list 7610.0 580) (list 7590.0 580) "C")
(command "_.CIRCLE" (list 7600 587) 5)
(command "-LAYER" "S" "Textos" "")
(command "-COLOR" "7")
(command "-TEXT" "S" "Standard" "J" "C" (list 7600 530) 10 0 "4xTEL")
(command "-LAYER" "S" "TVs" "")
(command "-COLOR" "5")
(command "_.PLINE" (list 7680.0 550) (list 7720.0 550) (list 7720.0 575) (list 7680.0 575) "C")
(command "_.PLINE" (list 7690.0 550) (list 7710.0 550) (list 7700 540) (list 7690.0 550) "")
(command "-LAYER" "S" "Textos" "")
(command "-COLOR" "7")
(command "-TEXT" "S" "Standard" "J" "C" (list 7700 530) 10 0 "2xTV")
(command "-LAYER" "S" "Camaras" "")
(command "-COLOR" "1")
(command "_.PLINE" (list 7790.0 550) (list 7810.0 550) (list 7810.0 565) (list 7790.0 565) "C")
(command "_.CIRCLE" (list 7800 557.5) 3)
(command "-LAYER" "S" "Textos" "")
(command "-COLOR" "7")
(command "-TEXT" "S" "Standard" "J" "C" (list 7800 530) 10 0 "1xCCTV")
(command "-LAYER" "S" "Datos" "")
(command "-COLOR" "1")
(command "_.PLINE" (list 7890.0 550) (list 7910.0 550) (list 7900 570) "C")
(command "-HATCH" "S" "L" "" "")
(command "-LAYER" "S" "Textos" "")
(command "-COLOR" "7")
(command "-TEXT" "S" "Standard" "J" "C" (list 7900 530) 10 0 "10xDATO")
(command "-LAYER" "S" "APs" "")
(command "-COLOR" "3")
(command "_.PLINE" (list 7490.0 750) (list 7510.0 750) (list 7500 775) (list 7490.0 750) "")
(command "_.CIRCLE" (list 7500 775) 10)
(command "_.CIRCLE" (list 7500 775) 21.25)
(command "_.CIRCLE" (list 7500 775) 30)
(command "-LAYER" "S" "Textos" "")
(command "-COLOR" "7")
(command "-TEXT" "S" "Standard" "J" "C" (list 7500 730) 10 0 "4xAP")
(command "-LAYER" "S" "Telefonos" "")
(command "-COLOR" "4")
(command "_.PLINE" (list 7590.0 750) (list 7610.0 750) (list 7610.0 780) (list 7590.0 780) "C")
(command "_.CIRCLE" (list 7600 787) 5)
(command "-LAYER" "S" "Textos" "")
(command "-COLOR" "7")
(command "-TEXT" "S" "Standard" "J" "C" (list 7600 730) 10 0 "4xTEL")
(command "-LAYER" "S" "TVs" "")
(command "-COLOR" "5")
(command "_.PLINE" (list 7680.0 750) (list 7720.0 750) (list 7720.0 775) (list 7680.0 775) "C")
(command "_.PLINE" (list 7690.0 750) (list 7710.0 750) (list 7700 740) (list 7690.0 750) "")
(command "-LAYER" "S" "Textos" "")
(command "-COLOR" "7")
(command "-TEXT" "S" "Standard" "J" "C" (list 7700 730) 10 0 "2xTV")
(command "-LAYER" "S" "Camaras" "")
(command "-COLOR" "1")
(command "_.PLINE" (list 7790.0 750) (list 7810.0 750) (list 7810.0 765) (list 7790.0 765) "C")
(command "_.CIRCLE" (list 7800 757.5) 3)
(command "-LAYER" "S" "Textos" "")
(command "-COLOR" "7")
(command "-TEXT" "S" "Standard" "J" "C" (list 7800 730) 10 0 "1xCCTV")
(command "-LAYER" "S" "Datos" "")
(command "-COLOR" "1")
(command "_.PLINE" (list 7890.0 750) (list 7910.0 750) (list 7900 770) "C")
(command "-HATCH" "S" "L" "" "")
(command "-LAYER" "S" "Textos" "")
(command "-COLOR" "7")
(command "-TEXT" "S" "Standard" "J" "C" (list 7900 730) 10 0 "10xDATO")
(command "-LAYER" "S" "APs" "")
(command "-COLOR" "3")
(command "_.PLINE" (list 7490.0 950) (list 7510.0 950) (list 7500 975) (list 7490.0 950) "")
(command "_.CIRCLE" (list 7500 975) 10)
(command "_.CIRCLE" (list 7500 975) 21.25)
(command "_.CIRCLE" (list 7500 975) 30)
(command "-LAYER" "S" "Textos" "")
(command "-COLOR" "7")
(command "-TEXT" "S" "Standard" "J" "C" (list 7500 930) 10 0 "4xAP")
(command "-LAYER" "S" "Telefonos" "")
(command "-COLOR" "4")
(command "_.PLINE" (list 7590.0 950) (list 7610.0 950) (list 7610.0 980) (list 7590.0 980) "C")
(command "_.CIRCLE" (list 7600 987) 5)
(command "-LAYER" "S" "Textos" "")
(command "-COLOR" "7")
(command "-TEXT" "S" "Standard" "J" "C" (list 7600 930) 10 0 "4xTEL")
(command "-LAYER" "S" "TVs" "")
(command "-COLOR" "5")
(command "_.PLINE" (list 7680.0 950) (list 7720.0 950) (list 7720.0 975) (list 7680.0 975) "C")
(command "_.PLINE" (list 7690.0 950) (list 7710.0 950) (list 7700 940) (list 7690.0 950) "")
(command "-LAYER" "S" "Textos" "")
(command "-COLOR" "7")
(command "-TEXT" "S" "Standard" "J" "C" (list 7700 930) 10 0 "2xTV")
(command "-LAYER" "S" "Camaras" "")
(command "-COLOR" "1")
(command "_.PLINE" (list 7790.0 950) (list 7810.0 950) (list 7810.0 965) (list 7790.0 965) "C")
(command "_.CIRCLE" (list 7800 957.5) 3)
(command "-LAYER" "S" "Textos" "")
(command "-COLOR" "7")
(command "-TEXT" "S" "Standard" "J" "C" (list 7800 930) 10 0 "1xCCTV")
(command "-LAYER" "S" "Datos" "")
(command "-COLOR" "1")
(command "_.PLINE" (list 7890.0 950) (list 7910.0 950) (list 7900 970) "C")
(command "-HATCH" "S" "L" "" "")
(command "-LAYER" "S" "Textos" "")
(command "-COLOR" "7")
(command "-TEXT" "S" "Standard" "J" "C" (list 7900 930) 10 0 "10xDATO")
(command "-LAYER" "S" "APs" "")
(command "-COLOR" "3")
(command "_.PLINE" (list 7490.0 1150) (list 7510.0 1150) (list 7500 1175) (list 7490.0 1150) "")
(command "_.CIRCLE" (list 7500 1175) 10)
(command "_.CIRCLE" (list 7500 1175) 21.25)
(command "_.CIRCLE" (list 7500 1175) 30)
(command "-LAYER" "S" "Textos" "")
(command "-COLOR" "7")
(command "-TEXT" "S" "Standard" "J" "C" (list 7500 1130) 10 0 "4xAP")
(command "-LAYER" "S" "Telefonos" "")
(command "-COLOR" "4")
(command "_.PLINE" (list 7590.0 1150) (list 7610.0 1150) (list 7610.0 1180) (list 7590.0 1180) "C")
(command "_.CIRCLE" (list 7600 1187) 5)
(command "-LAYER" "S" "Textos" "")
(command "-COLOR" "7")
(command "-TEXT" "S" "Standard" "J" "C" (list 7600 1130) 10 0 "4xTEL")
(command "-LAYER" "S" "TVs" "")
(command "-COLOR" "5")
(command "_.PLINE" (list 7680.0 1150) (list 7720.0 1150) (list 7720.0 1175) (list 7680.0 1175) "C")
(command "_.PLINE" (list 7690.0 1150) (list 7710.0 1150) (list 7700 1140) (list 7690.0 1150) "")
(command "-LAYER" "S" "Textos" "")
(command "-COLOR" "7")
(command "-TEXT" "S" "Standard" "J" "C" (list 7700 1130) 10 0 "2xTV")
(command "-LAYER" "S" "Camaras" "")
(command "-COLOR" "1")
(command "_.PLINE" (list 7790.0 1150) (list 7810.0 1150) (list 7810.0 1165) (list 7790.0 1165) "C")
(command "_.CIRCLE" (list 7800 1157.5) 3)
(command "-LAYER" "S" "Textos" "")
(command "-COLOR" "7")
(command "-TEXT" "S" "Standard" "J" "C" (list 7800 1130) 10 0 "1xCCTV")
(command "-LAYER" "S" "Datos" "")
(command "-COLOR" "1")
(command "_.PLINE" (list 7890.0 1150) (list 7910.0 1150) (list 7900 1170) "C")
(command "-HATCH" "S" "L" "" "")
(command "-LAYER" "S" "Textos" "")
(command "-COLOR" "7")
(command "-TEXT" "S" "Standard" "J" "C" (list 7900 1130) 10 0 "10xDATO")
(command "-LAYER" "S" "APs" "")
(command "-COLOR" "3")
(command "_.PLINE" (list 7490.0 1350) (list 7510.0 1350) (list 7500 1375) (list 7490.0 1350) "")
(command "_.CIRCLE" (list 7500 1375) 10)
(command "_.CIRCLE" (list 7500 1375) 21.25)
(command "_.CIRCLE" (list 7500 1375) 30)
(command "-LAYER" "S" "Textos" "")
(command "-COLOR" "7")
(command "-TEXT" "S" "Standard" "J" "C" (list 7500 1330) 10 0 "4xAP")
(command "-LAYER" "S" "Telefonos" "")
(command "-COLOR" "4")
(command "_.PLINE" (list 7590.0 1350) (list 7610.0 1350) (list 7610.0 1380) (list 7590.0 1380) "C")
(command "_.CIRCLE" (list 7600 1387) 5)
(command "-LAYER" "S" "Textos" "")
(command "-COLOR" "7")
(command "-TEXT" "S" "Standard" "J" "C" (list 7600 1330) 10 0 "4xTEL")
(command "-LAYER" "S" "TVs" "")
(command "-COLOR" "5")
(command "_.PLINE" (list 7680.0 1350) (list 7720.0 1350) (list 7720.0 1375) (list 7680.0 1375) "C")
(command "_.PLINE" (list 7690.0 1350) (list 7710.0 1350) (list 7700 1340) (list 7690.0 1350) "")
(command "-LAYER" "S" "Textos" "")
(command "-COLOR" "7")
(command "-TEXT" "S" "Standard" "J" "C" (list 7700 1330) 10 0 "2xTV")
(command "-LAYER" "S" "Camaras" "")
(command "-COLOR" "1")
(command "_.PLINE" (list 7790.0 1350) (list 7810.0 1350) (list 7810.0 1365) (list 7790.0 1365) "C")
(command "_.CIRCLE" (list 7800 1357.5) 3)
(command "-LAYER" "S" "Textos" "")
(command "-COLOR" "7")
(command "-TEXT" "S" "Standard" "J" "C" (list 7800 1330) 10 0 "1xCCTV")
(command "-LAYER" "S" "Datos" "")
(command "-COLOR" "1")
(command "_.PLINE" (list 7890.0 1350) (list 7910.0 1350) (list 7900 1370) "C")
(command "-HATCH" "S" "L" "" "")
(command "-LAYER" "S" "Textos" "")
(command "-COLOR" "7")
(command "-TEXT" "S" "Standard" "J" "C" (list 7900 1330) 10 0 "10xDATO")
(command "-LAYER" "S" "APs" "")
(command "-COLOR" "3")
(command "_.PLINE" (list 7490.0 1550) (list 7510.0 1550) (list 7500 1575) (list 7490.0 1550) "")
(command "_.CIRCLE" (list 7500 1575) 10)
(command "_.CIRCLE" (list 7500 1575) 21.25)
(command "_.CIRCLE" (list 7500 1575) 30)
(command "-LAYER" "S" "Textos" "")
(command "-COLOR" "7")
(command "-TEXT" "S" "Standard" "J" "C" (list 7500 1530) 10 0 "2xAP")
(command "-LAYER" "S" "Telefonos" "")
(command "-COLOR" "4")
(command "_.PLINE" (list 7590.0 1550) (list 7610.0 1550) (list 7610.0 1580) (list 7590.0 1580) "C")
(command "_.CIRCLE" (list 7600 1587) 5)
(command "-LAYER" "S" "Textos" "")
(command "-COLOR" "7")
(command "-TEXT" "S" "Standard" "J" "C" (list 7600 1530) 10 0 "2xTEL")
(command "-LAYER" "S" "TVs" "")
(command "-COLOR" "5")
(command "_.PLINE" (list 7680.0 1550) (list 7720.0 1550) (list 7720.0 1575) (list 7680.0 1575) "C")
(command "_.PLINE" (list 7690.0 1550) (list 7710.0 1550) (list 7700 1540) (list 7690.0 1550) "")
(command "-LAYER" "S" "Textos" "")
(command "-COLOR" "7")
(command "-TEXT" "S" "Standard" "J" "C" (list 7700 1530) 10 0 "1xTV")
(command "-LAYER" "S" "Camaras" "")
(command "-COLOR" "1")
(command "_.PLINE" (list 7790.0 1550) (list 7810.0 1550) (list 7810.0 1565) (list 7790.0 1565) "C")
(command "_.CIRCLE" (list 7800 1557.5) 3)
(command "-LAYER" "S" "Textos" "")
(command "-COLOR" "7")
(command "-TEXT" "S" "Standard" "J" "C" (list 7800 1530) 10 0 "1xCCTV")
(command "-LAYER" "S" "Datos" "")
(command "-COLOR" "1")
(command "_.PLINE" (list 7890.0 1550) (list 7910.0 1550) (list 7900 1570) "C")
(command "-HATCH" "S" "L" "" "")
(command "-LAYER" "S" "Textos" "")
(command "-COLOR" "7")
(command "-TEXT" "S" "Standard" "J" "C" (list 7900 1530) 10 0 "6xDATO")
(princ "DONE.")

; === DIBUJAR TORRE: IDF8 ===
(princ "\n>> Dibujando Torre: IDF8...")
(command "-LAYER" "S" "Textos" "")
(command "-COLOR" "7")
(command "-TEXT" "S" "Standard" "J" "C" (list 8500 150) 25 0 "IDF8")
(princ "\n   - Dibujando switches...")
(command "-LAYER" "S" "Switches" "")
(command "-COLOR" "6")
(command "_.PLINE" (list 8550 -200) (list 8670 -200) (list 8670 -160) (list 8550 -160) "C")
(command "-LAYER" "S" "Textos" "")
(command "-COLOR" "7")
(command "-TEXT" "S" "Standard" "J" "C" (list 8555 -185) 8 0 "SW-CCTV (DS-3E3728F)")
(command "-LAYER" "S" "Switches" "")
(command "-COLOR" "6")
(command "_.PLINE" (list 8550 -140) (list 8670 -140) (list 8670 -100) (list 8550 -100) "C")
(command "-LAYER" "S" "Textos" "")
(command "-COLOR" "7")
(command "-TEXT" "S" "Standard" "J" "C" (list 8555 -125) 8 0 "SW-DATA (Meraki MS225)")
(command "-LAYER" "S" "Switches" "")
(command "-COLOR" "6")
(command "_.PLINE" (list 8550 -80) (list 8670 -80) (list 8670 -40) (list 8550 -40) "C")
(command "-LAYER" "S" "Textos" "")
(command "-COLOR" "7")
(command "-TEXT" "S" "Standard" "J" "C" (list 8555 -65) 8 0 "SW-IPTV (RG-NBS6002)")
(command "-LAYER" "S" "Switches" "")
(command "-COLOR" "6")
(command "_.PLINE" (list 8550 -20) (list 8670 -20) (list 8670 20) (list 8550 20) "C")
(command "-LAYER" "S" "Textos" "")
(command "-COLOR" "7")
(command "-TEXT" "S" "Standard" "J" "C" (list 8555 -5) 8 0 "SW-TEL (Meraki MS225)")
(command "-LAYER" "S" "Switches" "")
(command "-COLOR" "6")
(command "_.PLINE" (list 8550 40) (list 8670 40) (list 8670 80) (list 8550 80) "C")
(command "-LAYER" "S" "Textos" "")
(command "-COLOR" "7")
(command "-TEXT" "S" "Standard" "J" "C" (list 8555 55) 8 0 "SW-WIFI (Meraki MS225)")
(princ "DONE.")
(princ "\n   - Dibujando dispositivos por nivel...")
(command "-LAYER" "S" "APs" "")
(command "-COLOR" "3")
(command "_.PLINE" (list 8540.0 150) (list 8560.0 150) (list 8550 175) (list 8540.0 150) "")
(command "_.CIRCLE" (list 8550 175) 10)
(command "_.CIRCLE" (list 8550 175) 21.25)
(command "_.CIRCLE" (list 8550 175) 30)
(command "-LAYER" "S" "Textos" "")
(command "-COLOR" "7")
(command "-TEXT" "S" "Standard" "J" "C" (list 8550 130) 10 0 "1xAP")
(command "-LAYER" "S" "Telefonos" "")
(command "-COLOR" "4")
(command "_.PLINE" (list 8640.0 150) (list 8660.0 150) (list 8660.0 180) (list 8640.0 180) "C")
(command "_.CIRCLE" (list 8650 187) 5)
(command "-LAYER" "S" "Textos" "")
(command "-COLOR" "7")
(command "-TEXT" "S" "Standard" "J" "C" (list 8650 130) 10 0 "2xTEL")
(command "-LAYER" "S" "TVs" "")
(command "-COLOR" "5")
(command "_.PLINE" (list 8730.0 150) (list 8770.0 150) (list 8770.0 175) (list 8730.0 175) "C")
(command "_.PLINE" (list 8740.0 150) (list 8760.0 150) (list 8750 140) (list 8740.0 150) "")
(command "-LAYER" "S" "Textos" "")
(command "-COLOR" "7")
(command "-TEXT" "S" "Standard" "J" "C" (list 8750 130) 10 0 "1xTV")
(command "-LAYER" "S" "Camaras" "")
(command "-COLOR" "1")
(command "_.PLINE" (list 8840.0 150) (list 8860.0 150) (list 8860.0 165) (list 8840.0 165) "C")
(command "_.CIRCLE" (list 8850 157.5) 3)
(command "-LAYER" "S" "Textos" "")
(command "-COLOR" "7")
(command "-TEXT" "S" "Standard" "J" "C" (list 8850 130) 10 0 "1xCCTV")
(command "-LAYER" "S" "Datos" "")
(command "-COLOR" "1")
(command "_.PLINE" (list 8940.0 150) (list 8960.0 150) (list 8950 170) "C")
(command "-HATCH" "S" "L" "" "")
(command "-LAYER" "S" "Textos" "")
(command "-COLOR" "7")
(command "-TEXT" "S" "Standard" "J" "C" (list 8950 130) 10 0 "5xDATO")
(command "-LAYER" "S" "APs" "")
(command "-COLOR" "3")
(command "_.PLINE" (list 8540.0 350) (list 8560.0 350) (list 8550 375) (list 8540.0 350) "")
(command "_.CIRCLE" (list 8550 375) 10)
(command "_.CIRCLE" (list 8550 375) 21.25)
(command "_.CIRCLE" (list 8550 375) 30)
(command "-LAYER" "S" "Textos" "")
(command "-COLOR" "7")
(command "-TEXT" "S" "Standard" "J" "C" (list 8550 330) 10 0 "4xAP")
(command "-LAYER" "S" "Telefonos" "")
(command "-COLOR" "4")
(command "_.PLINE" (list 8640.0 350) (list 8660.0 350) (list 8660.0 380) (list 8640.0 380) "C")
(command "_.CIRCLE" (list 8650 387) 5)
(command "-LAYER" "S" "Textos" "")
(command "-COLOR" "7")
(command "-TEXT" "S" "Standard" "J" "C" (list 8650 330) 10 0 "5xTEL")
(command "-LAYER" "S" "TVs" "")
(command "-COLOR" "5")
(command "_.PLINE" (list 8730.0 350) (list 8770.0 350) (list 8770.0 375) (list 8730.0 375) "C")
(command "_.PLINE" (list 8740.0 350) (list 8760.0 350) (list 8750 340) (list 8740.0 350) "")
(command "-LAYER" "S" "Textos" "")
(command "-COLOR" "7")
(command "-TEXT" "S" "Standard" "J" "C" (list 8750 330) 10 0 "3xTV")
(command "-LAYER" "S" "Camaras" "")
(command "-COLOR" "1")
(command "_.PLINE" (list 8840.0 350) (list 8860.0 350) (list 8860.0 365) (list 8840.0 365) "C")
(command "_.CIRCLE" (list 8850 357.5) 3)
(command "-LAYER" "S" "Textos" "")
(command "-COLOR" "7")
(command "-TEXT" "S" "Standard" "J" "C" (list 8850 330) 10 0 "2xCCTV")
(command "-LAYER" "S" "Datos" "")
(command "-COLOR" "1")
(command "_.PLINE" (list 8940.0 350) (list 8960.0 350) (list 8950 370) "C")
(command "-HATCH" "S" "L" "" "")
(command "-LAYER" "S" "Textos" "")
(command "-COLOR" "7")
(command "-TEXT" "S" "Standard" "J" "C" (list 8950 330) 10 0 "12xDATO")
(command "-LAYER" "S" "APs" "")
(command "-COLOR" "3")
(command "_.PLINE" (list 8540.0 550) (list 8560.0 550) (list 8550 575) (list 8540.0 550) "")
(command "_.CIRCLE" (list 8550 575) 10)
(command "_.CIRCLE" (list 8550 575) 21.25)
(command "_.CIRCLE" (list 8550 575) 30)
(command "-LAYER" "S" "Textos" "")
(command "-COLOR" "7")
(command "-TEXT" "S" "Standard" "J" "C" (list 8550 530) 10 0 "4xAP")
(command "-LAYER" "S" "Telefonos" "")
(command "-COLOR" "4")
(command "_.PLINE" (list 8640.0 550) (list 8660.0 550) (list 8660.0 580) (list 8640.0 580) "C")
(command "_.CIRCLE" (list 8650 587) 5)
(command "-LAYER" "S" "Textos" "")
(command "-COLOR" "7")
(command "-TEXT" "S" "Standard" "J" "C" (list 8650 530) 10 0 "4xTEL")
(command "-LAYER" "S" "TVs" "")
(command "-COLOR" "5")
(command "_.PLINE" (list 8730.0 550) (list 8770.0 550) (list 8770.0 575) (list 8730.0 575) "C")
(command "_.PLINE" (list 8740.0 550) (list 8760.0 550) (list 8750 540) (list 8740.0 550) "")
(command "-LAYER" "S" "Textos" "")
(command "-COLOR" "7")
(command "-TEXT" "S" "Standard" "J" "C" (list 8750 530) 10 0 "2xTV")
(command "-LAYER" "S" "Camaras" "")
(command "-COLOR" "1")
(command "_.PLINE" (list 8840.0 550) (list 8860.0 550) (list 8860.0 565) (list 8840.0 565) "C")
(command "_.CIRCLE" (list 8850 557.5) 3)
(command "-LAYER" "S" "Textos" "")
(command "-COLOR" "7")
(command "-TEXT" "S" "Standard" "J" "C" (list 8850 530) 10 0 "1xCCTV")
(command "-LAYER" "S" "Datos" "")
(command "-COLOR" "1")
(command "_.PLINE" (list 8940.0 550) (list 8960.0 550) (list 8950 570) "C")
(command "-HATCH" "S" "L" "" "")
(command "-LAYER" "S" "Textos" "")
(command "-COLOR" "7")
(command "-TEXT" "S" "Standard" "J" "C" (list 8950 530) 10 0 "10xDATO")
(command "-LAYER" "S" "APs" "")
(command "-COLOR" "3")
(command "_.PLINE" (list 8540.0 750) (list 8560.0 750) (list 8550 775) (list 8540.0 750) "")
(command "_.CIRCLE" (list 8550 775) 10)
(command "_.CIRCLE" (list 8550 775) 21.25)
(command "_.CIRCLE" (list 8550 775) 30)
(command "-LAYER" "S" "Textos" "")
(command "-COLOR" "7")
(command "-TEXT" "S" "Standard" "J" "C" (list 8550 730) 10 0 "4xAP")
(command "-LAYER" "S" "Telefonos" "")
(command "-COLOR" "4")
(command "_.PLINE" (list 8640.0 750) (list 8660.0 750) (list 8660.0 780) (list 8640.0 780) "C")
(command "_.CIRCLE" (list 8650 787) 5)
(command "-LAYER" "S" "Textos" "")
(command "-COLOR" "7")
(command "-TEXT" "S" "Standard" "J" "C" (list 8650 730) 10 0 "4xTEL")
(command "-LAYER" "S" "TVs" "")
(command "-COLOR" "5")
(command "_.PLINE" (list 8730.0 750) (list 8770.0 750) (list 8770.0 775) (list 8730.0 775) "C")
(command "_.PLINE" (list 8740.0 750) (list 8760.0 750) (list 8750 740) (list 8740.0 750) "")
(command "-LAYER" "S" "Textos" "")
(command "-COLOR" "7")
(command "-TEXT" "S" "Standard" "J" "C" (list 8750 730) 10 0 "2xTV")
(command "-LAYER" "S" "Camaras" "")
(command "-COLOR" "1")
(command "_.PLINE" (list 8840.0 750) (list 8860.0 750) (list 8860.0 765) (list 8840.0 765) "C")
(command "_.CIRCLE" (list 8850 757.5) 3)
(command "-LAYER" "S" "Textos" "")
(command "-COLOR" "7")
(command "-TEXT" "S" "Standard" "J" "C" (list 8850 730) 10 0 "1xCCTV")
(command "-LAYER" "S" "Datos" "")
(command "-COLOR" "1")
(command "_.PLINE" (list 8940.0 750) (list 8960.0 750) (list 8950 770) "C")
(command "-HATCH" "S" "L" "" "")
(command "-LAYER" "S" "Textos" "")
(command "-COLOR" "7")
(command "-TEXT" "S" "Standard" "J" "C" (list 8950 730) 10 0 "10xDATO")
(command "-LAYER" "S" "APs" "")
(command "-COLOR" "3")
(command "_.PLINE" (list 8540.0 950) (list 8560.0 950) (list 8550 975) (list 8540.0 950) "")
(command "_.CIRCLE" (list 8550 975) 10)
(command "_.CIRCLE" (list 8550 975) 21.25)
(command "_.CIRCLE" (list 8550 975) 30)
(command "-LAYER" "S" "Textos" "")
(command "-COLOR" "7")
(command "-TEXT" "S" "Standard" "J" "C" (list 8550 930) 10 0 "4xAP")
(command "-LAYER" "S" "Telefonos" "")
(command "-COLOR" "4")
(command "_.PLINE" (list 8640.0 950) (list 8660.0 950) (list 8660.0 980) (list 8640.0 980) "C")
(command "_.CIRCLE" (list 8650 987) 5)
(command "-LAYER" "S" "Textos" "")
(command "-COLOR" "7")
(command "-TEXT" "S" "Standard" "J" "C" (list 8650 930) 10 0 "4xTEL")
(command "-LAYER" "S" "TVs" "")
(command "-COLOR" "5")
(command "_.PLINE" (list 8730.0 950) (list 8770.0 950) (list 8770.0 975) (list 8730.0 975) "C")
(command "_.PLINE" (list 8740.0 950) (list 8760.0 950) (list 8750 940) (list 8740.0 950) "")
(command "-LAYER" "S" "Textos" "")
(command "-COLOR" "7")
(command "-TEXT" "S" "Standard" "J" "C" (list 8750 930) 10 0 "2xTV")
(command "-LAYER" "S" "Camaras" "")
(command "-COLOR" "1")
(command "_.PLINE" (list 8840.0 950) (list 8860.0 950) (list 8860.0 965) (list 8840.0 965) "C")
(command "_.CIRCLE" (list 8850 957.5) 3)
(command "-LAYER" "S" "Textos" "")
(command "-COLOR" "7")
(command "-TEXT" "S" "Standard" "J" "C" (list 8850 930) 10 0 "1xCCTV")
(command "-LAYER" "S" "Datos" "")
(command "-COLOR" "1")
(command "_.PLINE" (list 8940.0 950) (list 8960.0 950) (list 8950 970) "C")
(command "-HATCH" "S" "L" "" "")
(command "-LAYER" "S" "Textos" "")
(command "-COLOR" "7")
(command "-TEXT" "S" "Standard" "J" "C" (list 8950 930) 10 0 "10xDATO")
(command "-LAYER" "S" "APs" "")
(command "-COLOR" "3")
(command "_.PLINE" (list 8540.0 1150) (list 8560.0 1150) (list 8550 1175) (list 8540.0 1150) "")
(command "_.CIRCLE" (list 8550 1175) 10)
(command "_.CIRCLE" (list 8550 1175) 21.25)
(command "_.CIRCLE" (list 8550 1175) 30)
(command "-LAYER" "S" "Textos" "")
(command "-COLOR" "7")
(command "-TEXT" "S" "Standard" "J" "C" (list 8550 1130) 10 0 "4xAP")
(command "-LAYER" "S" "Telefonos" "")
(command "-COLOR" "4")
(command "_.PLINE" (list 8640.0 1150) (list 8660.0 1150) (list 8660.0 1180) (list 8640.0 1180) "C")
(command "_.CIRCLE" (list 8650 1187) 5)
(command "-LAYER" "S" "Textos" "")
(command "-COLOR" "7")
(command "-TEXT" "S" "Standard" "J" "C" (list 8650 1130) 10 0 "4xTEL")
(command "-LAYER" "S" "TVs" "")
(command "-COLOR" "5")
(command "_.PLINE" (list 8730.0 1150) (list 8770.0 1150) (list 8770.0 1175) (list 8730.0 1175) "C")
(command "_.PLINE" (list 8740.0 1150) (list 8760.0 1150) (list 8750 1140) (list 8740.0 1150) "")
(command "-LAYER" "S" "Textos" "")
(command "-COLOR" "7")
(command "-TEXT" "S" "Standard" "J" "C" (list 8750 1130) 10 0 "2xTV")
(command "-LAYER" "S" "Camaras" "")
(command "-COLOR" "1")
(command "_.PLINE" (list 8840.0 1150) (list 8860.0 1150) (list 8860.0 1165) (list 8840.0 1165) "C")
(command "_.CIRCLE" (list 8850 1157.5) 3)
(command "-LAYER" "S" "Textos" "")
(command "-COLOR" "7")
(command "-TEXT" "S" "Standard" "J" "C" (list 8850 1130) 10 0 "1xCCTV")
(command "-LAYER" "S" "Datos" "")
(command "-COLOR" "1")
(command "_.PLINE" (list 8940.0 1150) (list 8960.0 1150) (list 8950 1170) "C")
(command "-HATCH" "S" "L" "" "")
(command "-LAYER" "S" "Textos" "")
(command "-COLOR" "7")
(command "-TEXT" "S" "Standard" "J" "C" (list 8950 1130) 10 0 "10xDATO")
(command "-LAYER" "S" "APs" "")
(command "-COLOR" "3")
(command "_.PLINE" (list 8540.0 1350) (list 8560.0 1350) (list 8550 1375) (list 8540.0 1350) "")
(command "_.CIRCLE" (list 8550 1375) 10)
(command "_.CIRCLE" (list 8550 1375) 21.25)
(command "_.CIRCLE" (list 8550 1375) 30)
(command "-LAYER" "S" "Textos" "")
(command "-COLOR" "7")
(command "-TEXT" "S" "Standard" "J" "C" (list 8550 1330) 10 0 "4xAP")
(command "-LAYER" "S" "Telefonos" "")
(command "-COLOR" "4")
(command "_.PLINE" (list 8640.0 1350) (list 8660.0 1350) (list 8660.0 1380) (list 8640.0 1380) "C")
(command "_.CIRCLE" (list 8650 1387) 5)
(command "-LAYER" "S" "Textos" "")
(command "-COLOR" "7")
(command "-TEXT" "S" "Standard" "J" "C" (list 8650 1330) 10 0 "4xTEL")
(command "-LAYER" "S" "TVs" "")
(command "-COLOR" "5")
(command "_.PLINE" (list 8730.0 1350) (list 8770.0 1350) (list 8770.0 1375) (list 8730.0 1375) "C")
(command "_.PLINE" (list 8740.0 1350) (list 8760.0 1350) (list 8750 1340) (list 8740.0 1350) "")
(command "-LAYER" "S" "Textos" "")
(command "-COLOR" "7")
(command "-TEXT" "S" "Standard" "J" "C" (list 8750 1330) 10 0 "2xTV")
(command "-LAYER" "S" "Camaras" "")
(command "-COLOR" "1")
(command "_.PLINE" (list 8840.0 1350) (list 8860.0 1350) (list 8860.0 1365) (list 8840.0 1365) "C")
(command "_.CIRCLE" (list 8850 1357.5) 3)
(command "-LAYER" "S" "Textos" "")
(command "-COLOR" "7")
(command "-TEXT" "S" "Standard" "J" "C" (list 8850 1330) 10 0 "1xCCTV")
(command "-LAYER" "S" "Datos" "")
(command "-COLOR" "1")
(command "_.PLINE" (list 8940.0 1350) (list 8960.0 1350) (list 8950 1370) "C")
(command "-HATCH" "S" "L" "" "")
(command "-LAYER" "S" "Textos" "")
(command "-COLOR" "7")
(command "-TEXT" "S" "Standard" "J" "C" (list 8950 1330) 10 0 "10xDATO")
(command "-LAYER" "S" "APs" "")
(command "-COLOR" "3")
(command "_.PLINE" (list 8540.0 1550) (list 8560.0 1550) (list 8550 1575) (list 8540.0 1550) "")
(command "_.CIRCLE" (list 8550 1575) 10)
(command "_.CIRCLE" (list 8550 1575) 21.25)
(command "_.CIRCLE" (list 8550 1575) 30)
(command "-LAYER" "S" "Textos" "")
(command "-COLOR" "7")
(command "-TEXT" "S" "Standard" "J" "C" (list 8550 1530) 10 0 "2xAP")
(command "-LAYER" "S" "Telefonos" "")
(command "-COLOR" "4")
(command "_.PLINE" (list 8640.0 1550) (list 8660.0 1550) (list 8660.0 1580) (list 8640.0 1580) "C")
(command "_.CIRCLE" (list 8650 1587) 5)
(command "-LAYER" "S" "Textos" "")
(command "-COLOR" "7")
(command "-TEXT" "S" "Standard" "J" "C" (list 8650 1530) 10 0 "2xTEL")
(command "-LAYER" "S" "TVs" "")
(command "-COLOR" "5")
(command "_.PLINE" (list 8730.0 1550) (list 8770.0 1550) (list 8770.0 1575) (list 8730.0 1575) "C")
(command "_.PLINE" (list 8740.0 1550) (list 8760.0 1550) (list 8750 1540) (list 8740.0 1550) "")
(command "-LAYER" "S" "Textos" "")
(command "-COLOR" "7")
(command "-TEXT" "S" "Standard" "J" "C" (list 8750 1530) 10 0 "1xTV")
(command "-LAYER" "S" "Camaras" "")
(command "-COLOR" "1")
(command "_.PLINE" (list 8840.0 1550) (list 8860.0 1550) (list 8860.0 1565) (list 8840.0 1565) "C")
(command "_.CIRCLE" (list 8850 1557.5) 3)
(command "-LAYER" "S" "Textos" "")
(command "-COLOR" "7")
(command "-TEXT" "S" "Standard" "J" "C" (list 8850 1530) 10 0 "1xCCTV")
(command "-LAYER" "S" "Datos" "")
(command "-COLOR" "1")
(command "_.PLINE" (list 8940.0 1550) (list 8960.0 1550) (list 8950 1570) "C")
(command "-HATCH" "S" "L" "" "")
(command "-LAYER" "S" "Textos" "")
(command "-COLOR" "7")
(command "-TEXT" "S" "Standard" "J" "C" (list 8950 1530) 10 0 "6xDATO")
(princ "DONE.")

; === DIBUJAR TORRE: IDF9 ===
(princ "\n>> Dibujando Torre: IDF9...")
(command "-LAYER" "S" "Textos" "")
(command "-COLOR" "7")
(command "-TEXT" "S" "Standard" "J" "C" (list 9550 150) 25 0 "IDF9")
(princ "\n   - Dibujando switches...")
(command "-LAYER" "S" "Switches" "")
(command "-COLOR" "6")
(command "_.PLINE" (list 9600 -200) (list 9720 -200) (list 9720 -160) (list 9600 -160) "C")
(command "-LAYER" "S" "Textos" "")
(command "-COLOR" "7")
(command "-TEXT" "S" "Standard" "J" "C" (list 9605 -185) 8 0 "SW-CCTV (DS-3E3728F)")
(command "-LAYER" "S" "Switches" "")
(command "-COLOR" "6")
(command "_.PLINE" (list 9600 -140) (list 9720 -140) (list 9720 -100) (list 9600 -100) "C")
(command "-LAYER" "S" "Textos" "")
(command "-COLOR" "7")
(command "-TEXT" "S" "Standard" "J" "C" (list 9605 -125) 8 0 "SW-DATA (Meraki MS225)")
(command "-LAYER" "S" "Switches" "")
(command "-COLOR" "6")
(command "_.PLINE" (list 9600 -80) (list 9720 -80) (list 9720 -40) (list 9600 -40) "C")
(command "-LAYER" "S" "Textos" "")
(command "-COLOR" "7")
(command "-TEXT" "S" "Standard" "J" "C" (list 9605 -65) 8 0 "SW-IPTV (RG-NBS6002)")
(command "-LAYER" "S" "Switches" "")
(command "-COLOR" "6")
(command "_.PLINE" (list 9600 -20) (list 9720 -20) (list 9720 20) (list 9600 20) "C")
(command "-LAYER" "S" "Textos" "")
(command "-COLOR" "7")
(command "-TEXT" "S" "Standard" "J" "C" (list 9605 -5) 8 0 "SW-TEL (Meraki MS225)")
(command "-LAYER" "S" "Switches" "")
(command "-COLOR" "6")
(command "_.PLINE" (list 9600 40) (list 9720 40) (list 9720 80) (list 9600 80) "C")
(command "-LAYER" "S" "Textos" "")
(command "-COLOR" "7")
(command "-TEXT" "S" "Standard" "J" "C" (list 9605 55) 8 0 "SW-WIFI (Meraki MS225)")
(princ "DONE.")
(princ "\n   - Dibujando dispositivos por nivel...")
(command "-LAYER" "S" "Telefonos" "")
(command "-COLOR" "4")
(command "_.PLINE" (list 9590.0 150) (list 9610.0 150) (list 9610.0 180) (list 9590.0 180) "C")
(command "_.CIRCLE" (list 9600 187) 5)
(command "-LAYER" "S" "Textos" "")
(command "-COLOR" "7")
(command "-TEXT" "S" "Standard" "J" "C" (list 9600 130) 10 0 "1xTEL")
(command "-LAYER" "S" "Camaras" "")
(command "-COLOR" "1")
(command "_.PLINE" (list 9690.0 150) (list 9710.0 150) (list 9710.0 165) (list 9690.0 165) "C")
(command "_.CIRCLE" (list 9700 157.5) 3)
(command "-LAYER" "S" "Textos" "")
(command "-COLOR" "7")
(command "-TEXT" "S" "Standard" "J" "C" (list 9700 130) 10 0 "1xCCTV")
(command "-LAYER" "S" "Datos" "")
(command "-COLOR" "1")
(command "_.PLINE" (list 9790.0 150) (list 9810.0 150) (list 9800 170) "C")
(command "-HATCH" "S" "L" "" "")
(command "-LAYER" "S" "Textos" "")
(command "-COLOR" "7")
(command "-TEXT" "S" "Standard" "J" "C" (list 9800 130) 10 0 "3xDATO")
(command "-LAYER" "S" "APs" "")
(command "-COLOR" "3")
(command "_.PLINE" (list 9590.0 350) (list 9610.0 350) (list 9600 375) (list 9590.0 350) "")
(command "_.CIRCLE" (list 9600 375) 10)
(command "_.CIRCLE" (list 9600 375) 21.25)
(command "_.CIRCLE" (list 9600 375) 30)
(command "-LAYER" "S" "Textos" "")
(command "-COLOR" "7")
(command "-TEXT" "S" "Standard" "J" "C" (list 9600 330) 10 0 "4xAP")
(command "-LAYER" "S" "Telefonos" "")
(command "-COLOR" "4")
(command "_.PLINE" (list 9690.0 350) (list 9710.0 350) (list 9710.0 380) (list 9690.0 380) "C")
(command "_.CIRCLE" (list 9700 387) 5)
(command "-LAYER" "S" "Textos" "")
(command "-COLOR" "7")
(command "-TEXT" "S" "Standard" "J" "C" (list 9700 330) 10 0 "5xTEL")
(command "-LAYER" "S" "TVs" "")
(command "-COLOR" "5")
(command "_.PLINE" (list 9780.0 350) (list 9820.0 350) (list 9820.0 375) (list 9780.0 375) "C")
(command "_.PLINE" (list 9790.0 350) (list 9810.0 350) (list 9800 340) (list 9790.0 350) "")
(command "-LAYER" "S" "Textos" "")
(command "-COLOR" "7")
(command "-TEXT" "S" "Standard" "J" "C" (list 9800 330) 10 0 "3xTV")
(command "-LAYER" "S" "Camaras" "")
(command "-COLOR" "1")
(command "_.PLINE" (list 9890.0 350) (list 9910.0 350) (list 9910.0 365) (list 9890.0 365) "C")
(command "_.CIRCLE" (list 9900 357.5) 3)
(command "-LAYER" "S" "Textos" "")
(command "-COLOR" "7")
(command "-TEXT" "S" "Standard" "J" "C" (list 9900 330) 10 0 "2xCCTV")
(command "-LAYER" "S" "Datos" "")
(command "-COLOR" "1")
(command "_.PLINE" (list 9990.0 350) (list 10010.0 350) (list 10000 370) "C")
(command "-HATCH" "S" "L" "" "")
(command "-LAYER" "S" "Textos" "")
(command "-COLOR" "7")
(command "-TEXT" "S" "Standard" "J" "C" (list 10000 330) 10 0 "12xDATO")
(command "-LAYER" "S" "APs" "")
(command "-COLOR" "3")
(command "_.PLINE" (list 9590.0 550) (list 9610.0 550) (list 9600 575) (list 9590.0 550) "")
(command "_.CIRCLE" (list 9600 575) 10)
(command "_.CIRCLE" (list 9600 575) 21.25)
(command "_.CIRCLE" (list 9600 575) 30)
(command "-LAYER" "S" "Textos" "")
(command "-COLOR" "7")
(command "-TEXT" "S" "Standard" "J" "C" (list 9600 530) 10 0 "4xAP")
(command "-LAYER" "S" "Telefonos" "")
(command "-COLOR" "4")
(command "_.PLINE" (list 9690.0 550) (list 9710.0 550) (list 9710.0 580) (list 9690.0 580) "C")
(command "_.CIRCLE" (list 9700 587) 5)
(command "-LAYER" "S" "Textos" "")
(command "-COLOR" "7")
(command "-TEXT" "S" "Standard" "J" "C" (list 9700 530) 10 0 "4xTEL")
(command "-LAYER" "S" "TVs" "")
(command "-COLOR" "5")
(command "_.PLINE" (list 9780.0 550) (list 9820.0 550) (list 9820.0 575) (list 9780.0 575) "C")
(command "_.PLINE" (list 9790.0 550) (list 9810.0 550) (list 9800 540) (list 9790.0 550) "")
(command "-LAYER" "S" "Textos" "")
(command "-COLOR" "7")
(command "-TEXT" "S" "Standard" "J" "C" (list 9800 530) 10 0 "2xTV")
(command "-LAYER" "S" "Camaras" "")
(command "-COLOR" "1")
(command "_.PLINE" (list 9890.0 550) (list 9910.0 550) (list 9910.0 565) (list 9890.0 565) "C")
(command "_.CIRCLE" (list 9900 557.5) 3)
(command "-LAYER" "S" "Textos" "")
(command "-COLOR" "7")
(command "-TEXT" "S" "Standard" "J" "C" (list 9900 530) 10 0 "1xCCTV")
(command "-LAYER" "S" "Datos" "")
(command "-COLOR" "1")
(command "_.PLINE" (list 9990.0 550) (list 10010.0 550) (list 10000 570) "C")
(command "-HATCH" "S" "L" "" "")
(command "-LAYER" "S" "Textos" "")
(command "-COLOR" "7")
(command "-TEXT" "S" "Standard" "J" "C" (list 10000 530) 10 0 "10xDATO")
(command "-LAYER" "S" "APs" "")
(command "-COLOR" "3")
(command "_.PLINE" (list 9590.0 750) (list 9610.0 750) (list 9600 775) (list 9590.0 750) "")
(command "_.CIRCLE" (list 9600 775) 10)
(command "_.CIRCLE" (list 9600 775) 21.25)
(command "_.CIRCLE" (list 9600 775) 30)
(command "-LAYER" "S" "Textos" "")
(command "-COLOR" "7")
(command "-TEXT" "S" "Standard" "J" "C" (list 9600 730) 10 0 "4xAP")
(command "-LAYER" "S" "Telefonos" "")
(command "-COLOR" "4")
(command "_.PLINE" (list 9690.0 750) (list 9710.0 750) (list 9710.0 780) (list 9690.0 780) "C")
(command "_.CIRCLE" (list 9700 787) 5)
(command "-LAYER" "S" "Textos" "")
(command "-COLOR" "7")
(command "-TEXT" "S" "Standard" "J" "C" (list 9700 730) 10 0 "4xTEL")
(command "-LAYER" "S" "TVs" "")
(command "-COLOR" "5")
(command "_.PLINE" (list 9780.0 750) (list 9820.0 750) (list 9820.0 775) (list 9780.0 775) "C")
(command "_.PLINE" (list 9790.0 750) (list 9810.0 750) (list 9800 740) (list 9790.0 750) "")
(command "-LAYER" "S" "Textos" "")
(command "-COLOR" "7")
(command "-TEXT" "S" "Standard" "J" "C" (list 9800 730) 10 0 "2xTV")
(command "-LAYER" "S" "Camaras" "")
(command "-COLOR" "1")
(command "_.PLINE" (list 9890.0 750) (list 9910.0 750) (list 9910.0 765) (list 9890.0 765) "C")
(command "_.CIRCLE" (list 9900 757.5) 3)
(command "-LAYER" "S" "Textos" "")
(command "-COLOR" "7")
(command "-TEXT" "S" "Standard" "J" "C" (list 9900 730) 10 0 "1xCCTV")
(command "-LAYER" "S" "Datos" "")
(command "-COLOR" "1")
(command "_.PLINE" (list 9990.0 750) (list 10010.0 750) (list 10000 770) "C")
(command "-HATCH" "S" "L" "" "")
(command "-LAYER" "S" "Textos" "")
(command "-COLOR" "7")
(command "-TEXT" "S" "Standard" "J" "C" (list 10000 730) 10 0 "10xDATO")
(command "-LAYER" "S" "APs" "")
(command "-COLOR" "3")
(command "_.PLINE" (list 9590.0 950) (list 9610.0 950) (list 9600 975) (list 9590.0 950) "")
(command "_.CIRCLE" (list 9600 975) 10)
(command "_.CIRCLE" (list 9600 975) 21.25)
(command "_.CIRCLE" (list 9600 975) 30)
(command "-LAYER" "S" "Textos" "")
(command "-COLOR" "7")
(command "-TEXT" "S" "Standard" "J" "C" (list 9600 930) 10 0 "4xAP")
(command "-LAYER" "S" "Telefonos" "")
(command "-COLOR" "4")
(command "_.PLINE" (list 9690.0 950) (list 9710.0 950) (list 9710.0 980) (list 9690.0 980) "C")
(command "_.CIRCLE" (list 9700 987) 5)
(command "-LAYER" "S" "Textos" "")
(command "-COLOR" "7")
(command "-TEXT" "S" "Standard" "J" "C" (list 9700 930) 10 0 "4xTEL")
(command "-LAYER" "S" "TVs" "")
(command "-COLOR" "5")
(command "_.PLINE" (list 9780.0 950) (list 9820.0 950) (list 9820.0 975) (list 9780.0 975) "C")
(command "_.PLINE" (list 9790.0 950) (list 9810.0 950) (list 9800 940) (list 9790.0 950) "")
(command "-LAYER" "S" "Textos" "")
(command "-COLOR" "7")
(command "-TEXT" "S" "Standard" "J" "C" (list 9800 930) 10 0 "2xTV")
(command "-LAYER" "S" "Camaras" "")
(command "-COLOR" "1")
(command "_.PLINE" (list 9890.0 950) (list 9910.0 950) (list 9910.0 965) (list 9890.0 965) "C")
(command "_.CIRCLE" (list 9900 957.5) 3)
(command "-LAYER" "S" "Textos" "")
(command "-COLOR" "7")
(command "-TEXT" "S" "Standard" "J" "C" (list 9900 930) 10 0 "1xCCTV")
(command "-LAYER" "S" "Datos" "")
(command "-COLOR" "1")
(command "_.PLINE" (list 9990.0 950) (list 10010.0 950) (list 10000 970) "C")
(command "-HATCH" "S" "L" "" "")
(command "-LAYER" "S" "Textos" "")
(command "-COLOR" "7")
(command "-TEXT" "S" "Standard" "J" "C" (list 10000 930) 10 0 "10xDATO")
(command "-LAYER" "S" "APs" "")
(command "-COLOR" "3")
(command "_.PLINE" (list 9590.0 1150) (list 9610.0 1150) (list 9600 1175) (list 9590.0 1150) "")
(command "_.CIRCLE" (list 9600 1175) 10)
(command "_.CIRCLE" (list 9600 1175) 21.25)
(command "_.CIRCLE" (list 9600 1175) 30)
(command "-LAYER" "S" "Textos" "")
(command "-COLOR" "7")
(command "-TEXT" "S" "Standard" "J" "C" (list 9600 1130) 10 0 "4xAP")
(command "-LAYER" "S" "Telefonos" "")
(command "-COLOR" "4")
(command "_.PLINE" (list 9690.0 1150) (list 9710.0 1150) (list 9710.0 1180) (list 9690.0 1180) "C")
(command "_.CIRCLE" (list 9700 1187) 5)
(command "-LAYER" "S" "Textos" "")
(command "-COLOR" "7")
(command "-TEXT" "S" "Standard" "J" "C" (list 9700 1130) 10 0 "4xTEL")
(command "-LAYER" "S" "TVs" "")
(command "-COLOR" "5")
(command "_.PLINE" (list 9780.0 1150) (list 9820.0 1150) (list 9820.0 1175) (list 9780.0 1175) "C")
(command "_.PLINE" (list 9790.0 1150) (list 9810.0 1150) (list 9800 1140) (list 9790.0 1150) "")
(command "-LAYER" "S" "Textos" "")
(command "-COLOR" "7")
(command "-TEXT" "S" "Standard" "J" "C" (list 9800 1130) 10 0 "2xTV")
(command "-LAYER" "S" "Camaras" "")
(command "-COLOR" "1")
(command "_.PLINE" (list 9890.0 1150) (list 9910.0 1150) (list 9910.0 1165) (list 9890.0 1165) "C")
(command "_.CIRCLE" (list 9900 1157.5) 3)
(command "-LAYER" "S" "Textos" "")
(command "-COLOR" "7")
(command "-TEXT" "S" "Standard" "J" "C" (list 9900 1130) 10 0 "1xCCTV")
(command "-LAYER" "S" "Datos" "")
(command "-COLOR" "1")
(command "_.PLINE" (list 9990.0 1150) (list 10010.0 1150) (list 10000 1170) "C")
(command "-HATCH" "S" "L" "" "")
(command "-LAYER" "S" "Textos" "")
(command "-COLOR" "7")
(command "-TEXT" "S" "Standard" "J" "C" (list 10000 1130) 10 0 "10xDATO")
(command "-LAYER" "S" "APs" "")
(command "-COLOR" "3")
(command "_.PLINE" (list 9590.0 1350) (list 9610.0 1350) (list 9600 1375) (list 9590.0 1350) "")
(command "_.CIRCLE" (list 9600 1375) 10)
(command "_.CIRCLE" (list 9600 1375) 21.25)
(command "_.CIRCLE" (list 9600 1375) 30)
(command "-LAYER" "S" "Textos" "")
(command "-COLOR" "7")
(command "-TEXT" "S" "Standard" "J" "C" (list 9600 1330) 10 0 "4xAP")
(command "-LAYER" "S" "Telefonos" "")
(command "-COLOR" "4")
(command "_.PLINE" (list 9690.0 1350) (list 9710.0 1350) (list 9710.0 1380) (list 9690.0 1380) "C")
(command "_.CIRCLE" (list 9700 1387) 5)
(command "-LAYER" "S" "Textos" "")
(command "-COLOR" "7")
(command "-TEXT" "S" "Standard" "J" "C" (list 9700 1330) 10 0 "4xTEL")
(command "-LAYER" "S" "TVs" "")
(command "-COLOR" "5")
(command "_.PLINE" (list 9780.0 1350) (list 9820.0 1350) (list 9820.0 1375) (list 9780.0 1375) "C")
(command "_.PLINE" (list 9790.0 1350) (list 9810.0 1350) (list 9800 1340) (list 9790.0 1350) "")
(command "-LAYER" "S" "Textos" "")
(command "-COLOR" "7")
(command "-TEXT" "S" "Standard" "J" "C" (list 9800 1330) 10 0 "2xTV")
(command "-LAYER" "S" "Camaras" "")
(command "-COLOR" "1")
(command "_.PLINE" (list 9890.0 1350) (list 9910.0 1350) (list 9910.0 1365) (list 9890.0 1365) "C")
(command "_.CIRCLE" (list 9900 1357.5) 3)
(command "-LAYER" "S" "Textos" "")
(command "-COLOR" "7")
(command "-TEXT" "S" "Standard" "J" "C" (list 9900 1330) 10 0 "1xCCTV")
(command "-LAYER" "S" "Datos" "")
(command "-COLOR" "1")
(command "_.PLINE" (list 9990.0 1350) (list 10010.0 1350) (list 10000 1370) "C")
(command "-HATCH" "S" "L" "" "")
(command "-LAYER" "S" "Textos" "")
(command "-COLOR" "7")
(command "-TEXT" "S" "Standard" "J" "C" (list 10000 1330) 10 0 "10xDATO")
(command "-LAYER" "S" "APs" "")
(command "-COLOR" "3")
(command "_.PLINE" (list 9590.0 1550) (list 9610.0 1550) (list 9600 1575) (list 9590.0 1550) "")
(command "_.CIRCLE" (list 9600 1575) 10)
(command "_.CIRCLE" (list 9600 1575) 21.25)
(command "_.CIRCLE" (list 9600 1575) 30)
(command "-LAYER" "S" "Textos" "")
(command "-COLOR" "7")
(command "-TEXT" "S" "Standard" "J" "C" (list 9600 1530) 10 0 "2xAP")
(command "-LAYER" "S" "Telefonos" "")
(command "-COLOR" "4")
(command "_.PLINE" (list 9690.0 1550) (list 9710.0 1550) (list 9710.0 1580) (list 9690.0 1580) "C")
(command "_.CIRCLE" (list 9700 1587) 5)
(command "-LAYER" "S" "Textos" "")
(command "-COLOR" "7")
(command "-TEXT" "S" "Standard" "J" "C" (list 9700 1530) 10 0 "2xTEL")
(command "-LAYER" "S" "TVs" "")
(command "-COLOR" "5")
(command "_.PLINE" (list 9780.0 1550) (list 9820.0 1550) (list 9820.0 1575) (list 9780.0 1575) "C")
(command "_.PLINE" (list 9790.0 1550) (list 9810.0 1550) (list 9800 1540) (list 9790.0 1550) "")
(command "-LAYER" "S" "Textos" "")
(command "-COLOR" "7")
(command "-TEXT" "S" "Standard" "J" "C" (list 9800 1530) 10 0 "1xTV")
(command "-LAYER" "S" "Camaras" "")
(command "-COLOR" "1")
(command "_.PLINE" (list 9890.0 1550) (list 9910.0 1550) (list 9910.0 1565) (list 9890.0 1565) "C")
(command "_.CIRCLE" (list 9900 1557.5) 3)
(command "-LAYER" "S" "Textos" "")
(command "-COLOR" "7")
(command "-TEXT" "S" "Standard" "J" "C" (list 9900 1530) 10 0 "1xCCTV")
(command "-LAYER" "S" "Datos" "")
(command "-COLOR" "1")
(command "_.PLINE" (list 9990.0 1550) (list 10010.0 1550) (list 10000 1570) "C")
(command "-HATCH" "S" "L" "" "")
(command "-LAYER" "S" "Textos" "")
(command "-COLOR" "7")
(command "-TEXT" "S" "Standard" "J" "C" (list 10000 1530) 10 0 "6xDATO")
(princ "DONE.")

; === DIBUJAR TORRE: IDF10 ===
(princ "\n>> Dibujando Torre: IDF10...")
(command "-LAYER" "S" "Textos" "")
(command "-COLOR" "7")
(command "-TEXT" "S" "Standard" "J" "C" (list 10600 150) 25 0 "IDF10")
(princ "\n   - Dibujando switches...")
(command "-LAYER" "S" "Switches" "")
(command "-COLOR" "6")
(command "_.PLINE" (list 10650 -200) (list 10770 -200) (list 10770 -160) (list 10650 -160) "C")
(command "-LAYER" "S" "Textos" "")
(command "-COLOR" "7")
(command "-TEXT" "S" "Standard" "J" "C" (list 10655 -185) 8 0 "SW-CCTV (DS-3E3728F)")
(command "-LAYER" "S" "Switches" "")
(command "-COLOR" "6")
(command "_.PLINE" (list 10650 -140) (list 10770 -140) (list 10770 -100) (list 10650 -100) "C")
(command "-LAYER" "S" "Textos" "")
(command "-COLOR" "7")
(command "-TEXT" "S" "Standard" "J" "C" (list 10655 -125) 8 0 "SW-DATA (Meraki MS225)")
(command "-LAYER" "S" "Switches" "")
(command "-COLOR" "6")
(command "_.PLINE" (list 10650 -80) (list 10770 -80) (list 10770 -40) (list 10650 -40) "C")
(command "-LAYER" "S" "Textos" "")
(command "-COLOR" "7")
(command "-TEXT" "S" "Standard" "J" "C" (list 10655 -65) 8 0 "SW-IPTV (RG-NBS6002)")
(command "-LAYER" "S" "Switches" "")
(command "-COLOR" "6")
(command "_.PLINE" (list 10650 -20) (list 10770 -20) (list 10770 20) (list 10650 20) "C")
(command "-LAYER" "S" "Textos" "")
(command "-COLOR" "7")
(command "-TEXT" "S" "Standard" "J" "C" (list 10655 -5) 8 0 "SW-TEL (Meraki MS225)")
(command "-LAYER" "S" "Switches" "")
(command "-COLOR" "6")
(command "_.PLINE" (list 10650 40) (list 10770 40) (list 10770 80) (list 10650 80) "C")
(command "-LAYER" "S" "Textos" "")
(command "-COLOR" "7")
(command "-TEXT" "S" "Standard" "J" "C" (list 10655 55) 8 0 "SW-WIFI (Meraki MS225)")
(princ "DONE.")
(princ "\n   - Dibujando dispositivos por nivel...")
(command "-LAYER" "S" "APs" "")
(command "-COLOR" "3")
(command "_.PLINE" (list 10640.0 150) (list 10660.0 150) (list 10650 175) (list 10640.0 150) "")
(command "_.CIRCLE" (list 10650 175) 10)
(command "_.CIRCLE" (list 10650 175) 21.25)
(command "_.CIRCLE" (list 10650 175) 30)
(command "-LAYER" "S" "Textos" "")
(command "-COLOR" "7")
(command "-TEXT" "S" "Standard" "J" "C" (list 10650 130) 10 0 "1xAP")
(command "-LAYER" "S" "Telefonos" "")
(command "-COLOR" "4")
(command "_.PLINE" (list 10740.0 150) (list 10760.0 150) (list 10760.0 180) (list 10740.0 180) "C")
(command "_.CIRCLE" (list 10750 187) 5)
(command "-LAYER" "S" "Textos" "")
(command "-COLOR" "7")
(command "-TEXT" "S" "Standard" "J" "C" (list 10750 130) 10 0 "2xTEL")
(command "-LAYER" "S" "TVs" "")
(command "-COLOR" "5")
(command "_.PLINE" (list 10830.0 150) (list 10870.0 150) (list 10870.0 175) (list 10830.0 175) "C")
(command "_.PLINE" (list 10840.0 150) (list 10860.0 150) (list 10850 140) (list 10840.0 150) "")
(command "-LAYER" "S" "Textos" "")
(command "-COLOR" "7")
(command "-TEXT" "S" "Standard" "J" "C" (list 10850 130) 10 0 "1xTV")
(command "-LAYER" "S" "Camaras" "")
(command "-COLOR" "1")
(command "_.PLINE" (list 10940.0 150) (list 10960.0 150) (list 10960.0 165) (list 10940.0 165) "C")
(command "_.CIRCLE" (list 10950 157.5) 3)
(command "-LAYER" "S" "Textos" "")
(command "-COLOR" "7")
(command "-TEXT" "S" "Standard" "J" "C" (list 10950 130) 10 0 "1xCCTV")
(command "-LAYER" "S" "Datos" "")
(command "-COLOR" "1")
(command "_.PLINE" (list 11040.0 150) (list 11060.0 150) (list 11050 170) "C")
(command "-HATCH" "S" "L" "" "")
(command "-LAYER" "S" "Textos" "")
(command "-COLOR" "7")
(command "-TEXT" "S" "Standard" "J" "C" (list 11050 130) 10 0 "5xDATO")
(command "-LAYER" "S" "APs" "")
(command "-COLOR" "3")
(command "_.PLINE" (list 10640.0 350) (list 10660.0 350) (list 10650 375) (list 10640.0 350) "")
(command "_.CIRCLE" (list 10650 375) 10)
(command "_.CIRCLE" (list 10650 375) 21.25)
(command "_.CIRCLE" (list 10650 375) 30)
(command "-LAYER" "S" "Textos" "")
(command "-COLOR" "7")
(command "-TEXT" "S" "Standard" "J" "C" (list 10650 330) 10 0 "4xAP")
(command "-LAYER" "S" "Telefonos" "")
(command "-COLOR" "4")
(command "_.PLINE" (list 10740.0 350) (list 10760.0 350) (list 10760.0 380) (list 10740.0 380) "C")
(command "_.CIRCLE" (list 10750 387) 5)
(command "-LAYER" "S" "Textos" "")
(command "-COLOR" "7")
(command "-TEXT" "S" "Standard" "J" "C" (list 10750 330) 10 0 "5xTEL")
(command "-LAYER" "S" "TVs" "")
(command "-COLOR" "5")
(command "_.PLINE" (list 10830.0 350) (list 10870.0 350) (list 10870.0 375) (list 10830.0 375) "C")
(command "_.PLINE" (list 10840.0 350) (list 10860.0 350) (list 10850 340) (list 10840.0 350) "")
(command "-LAYER" "S" "Textos" "")
(command "-COLOR" "7")
(command "-TEXT" "S" "Standard" "J" "C" (list 10850 330) 10 0 "3xTV")
(command "-LAYER" "S" "Camaras" "")
(command "-COLOR" "1")
(command "_.PLINE" (list 10940.0 350) (list 10960.0 350) (list 10960.0 365) (list 10940.0 365) "C")
(command "_.CIRCLE" (list 10950 357.5) 3)
(command "-LAYER" "S" "Textos" "")
(command "-COLOR" "7")
(command "-TEXT" "S" "Standard" "J" "C" (list 10950 330) 10 0 "2xCCTV")
(command "-LAYER" "S" "Datos" "")
(command "-COLOR" "1")
(command "_.PLINE" (list 11040.0 350) (list 11060.0 350) (list 11050 370) "C")
(command "-HATCH" "S" "L" "" "")
(command "-LAYER" "S" "Textos" "")
(command "-COLOR" "7")
(command "-TEXT" "S" "Standard" "J" "C" (list 11050 330) 10 0 "12xDATO")
(command "-LAYER" "S" "APs" "")
(command "-COLOR" "3")
(command "_.PLINE" (list 10640.0 550) (list 10660.0 550) (list 10650 575) (list 10640.0 550) "")
(command "_.CIRCLE" (list 10650 575) 10)
(command "_.CIRCLE" (list 10650 575) 21.25)
(command "_.CIRCLE" (list 10650 575) 30)
(command "-LAYER" "S" "Textos" "")
(command "-COLOR" "7")
(command "-TEXT" "S" "Standard" "J" "C" (list 10650 530) 10 0 "4xAP")
(command "-LAYER" "S" "Telefonos" "")
(command "-COLOR" "4")
(command "_.PLINE" (list 10740.0 550) (list 10760.0 550) (list 10760.0 580) (list 10740.0 580) "C")
(command "_.CIRCLE" (list 10750 587) 5)
(command "-LAYER" "S" "Textos" "")
(command "-COLOR" "7")
(command "-TEXT" "S" "Standard" "J" "C" (list 10750 530) 10 0 "4xTEL")
(command "-LAYER" "S" "TVs" "")
(command "-COLOR" "5")
(command "_.PLINE" (list 10830.0 550) (list 10870.0 550) (list 10870.0 575) (list 10830.0 575) "C")
(command "_.PLINE" (list 10840.0 550) (list 10860.0 550) (list 10850 540) (list 10840.0 550) "")
(command "-LAYER" "S" "Textos" "")
(command "-COLOR" "7")
(command "-TEXT" "S" "Standard" "J" "C" (list 10850 530) 10 0 "2xTV")
(command "-LAYER" "S" "Camaras" "")
(command "-COLOR" "1")
(command "_.PLINE" (list 10940.0 550) (list 10960.0 550) (list 10960.0 565) (list 10940.0 565) "C")
(command "_.CIRCLE" (list 10950 557.5) 3)
(command "-LAYER" "S" "Textos" "")
(command "-COLOR" "7")
(command "-TEXT" "S" "Standard" "J" "C" (list 10950 530) 10 0 "1xCCTV")
(command "-LAYER" "S" "Datos" "")
(command "-COLOR" "1")
(command "_.PLINE" (list 11040.0 550) (list 11060.0 550) (list 11050 570) "C")
(command "-HATCH" "S" "L" "" "")
(command "-LAYER" "S" "Textos" "")
(command "-COLOR" "7")
(command "-TEXT" "S" "Standard" "J" "C" (list 11050 530) 10 0 "10xDATO")
(command "-LAYER" "S" "APs" "")
(command "-COLOR" "3")
(command "_.PLINE" (list 10640.0 750) (list 10660.0 750) (list 10650 775) (list 10640.0 750) "")
(command "_.CIRCLE" (list 10650 775) 10)
(command "_.CIRCLE" (list 10650 775) 21.25)
(command "_.CIRCLE" (list 10650 775) 30)
(command "-LAYER" "S" "Textos" "")
(command "-COLOR" "7")
(command "-TEXT" "S" "Standard" "J" "C" (list 10650 730) 10 0 "4xAP")
(command "-LAYER" "S" "Telefonos" "")
(command "-COLOR" "4")
(command "_.PLINE" (list 10740.0 750) (list 10760.0 750) (list 10760.0 780) (list 10740.0 780) "C")
(command "_.CIRCLE" (list 10750 787) 5)
(command "-LAYER" "S" "Textos" "")
(command "-COLOR" "7")
(command "-TEXT" "S" "Standard" "J" "C" (list 10750 730) 10 0 "4xTEL")
(command "-LAYER" "S" "TVs" "")
(command "-COLOR" "5")
(command "_.PLINE" (list 10830.0 750) (list 10870.0 750) (list 10870.0 775) (list 10830.0 775) "C")
(command "_.PLINE" (list 10840.0 750) (list 10860.0 750) (list 10850 740) (list 10840.0 750) "")
(command "-LAYER" "S" "Textos" "")
(command "-COLOR" "7")
(command "-TEXT" "S" "Standard" "J" "C" (list 10850 730) 10 0 "2xTV")
(command "-LAYER" "S" "Camaras" "")
(command "-COLOR" "1")
(command "_.PLINE" (list 10940.0 750) (list 10960.0 750) (list 10960.0 765) (list 10940.0 765) "C")
(command "_.CIRCLE" (list 10950 757.5) 3)
(command "-LAYER" "S" "Textos" "")
(command "-COLOR" "7")
(command "-TEXT" "S" "Standard" "J" "C" (list 10950 730) 10 0 "1xCCTV")
(command "-LAYER" "S" "Datos" "")
(command "-COLOR" "1")
(command "_.PLINE" (list 11040.0 750) (list 11060.0 750) (list 11050 770) "C")
(command "-HATCH" "S" "L" "" "")
(command "-LAYER" "S" "Textos" "")
(command "-COLOR" "7")
(command "-TEXT" "S" "Standard" "J" "C" (list 11050 730) 10 0 "10xDATO")
(command "-LAYER" "S" "APs" "")
(command "-COLOR" "3")
(command "_.PLINE" (list 10640.0 950) (list 10660.0 950) (list 10650 975) (list 10640.0 950) "")
(command "_.CIRCLE" (list 10650 975) 10)
(command "_.CIRCLE" (list 10650 975) 21.25)
(command "_.CIRCLE" (list 10650 975) 30)
(command "-LAYER" "S" "Textos" "")
(command "-COLOR" "7")
(command "-TEXT" "S" "Standard" "J" "C" (list 10650 930) 10 0 "4xAP")
(command "-LAYER" "S" "Telefonos" "")
(command "-COLOR" "4")
(command "_.PLINE" (list 10740.0 950) (list 10760.0 950) (list 10760.0 980) (list 10740.0 980) "C")
(command "_.CIRCLE" (list 10750 987) 5)
(command "-LAYER" "S" "Textos" "")
(command "-COLOR" "7")
(command "-TEXT" "S" "Standard" "J" "C" (list 10750 930) 10 0 "4xTEL")
(command "-LAYER" "S" "TVs" "")
(command "-COLOR" "5")
(command "_.PLINE" (list 10830.0 950) (list 10870.0 950) (list 10870.0 975) (list 10830.0 975) "C")
(command "_.PLINE" (list 10840.0 950) (list 10860.0 950) (list 10850 940) (list 10840.0 950) "")
(command "-LAYER" "S" "Textos" "")
(command "-COLOR" "7")
(command "-TEXT" "S" "Standard" "J" "C" (list 10850 930) 10 0 "2xTV")
(command "-LAYER" "S" "Camaras" "")
(command "-COLOR" "1")
(command "_.PLINE" (list 10940.0 950) (list 10960.0 950) (list 10960.0 965) (list 10940.0 965) "C")
(command "_.CIRCLE" (list 10950 957.5) 3)
(command "-LAYER" "S" "Textos" "")
(command "-COLOR" "7")
(command "-TEXT" "S" "Standard" "J" "C" (list 10950 930) 10 0 "1xCCTV")
(command "-LAYER" "S" "Datos" "")
(command "-COLOR" "1")
(command "_.PLINE" (list 11040.0 950) (list 11060.0 950) (list 11050 970) "C")
(command "-HATCH" "S" "L" "" "")
(command "-LAYER" "S" "Textos" "")
(command "-COLOR" "7")
(command "-TEXT" "S" "Standard" "J" "C" (list 11050 930) 10 0 "10xDATO")
(command "-LAYER" "S" "APs" "")
(command "-COLOR" "3")
(command "_.PLINE" (list 10640.0 1150) (list 10660.0 1150) (list 10650 1175) (list 10640.0 1150) "")
(command "_.CIRCLE" (list 10650 1175) 10)
(command "_.CIRCLE" (list 10650 1175) 21.25)
(command "_.CIRCLE" (list 10650 1175) 30)
(command "-LAYER" "S" "Textos" "")
(command "-COLOR" "7")
(command "-TEXT" "S" "Standard" "J" "C" (list 10650 1130) 10 0 "4xAP")
(command "-LAYER" "S" "Telefonos" "")
(command "-COLOR" "4")
(command "_.PLINE" (list 10740.0 1150) (list 10760.0 1150) (list 10760.0 1180) (list 10740.0 1180) "C")
(command "_.CIRCLE" (list 10750 1187) 5)
(command "-LAYER" "S" "Textos" "")
(command "-COLOR" "7")
(command "-TEXT" "S" "Standard" "J" "C" (list 10750 1130) 10 0 "4xTEL")
(command "-LAYER" "S" "TVs" "")
(command "-COLOR" "5")
(command "_.PLINE" (list 10830.0 1150) (list 10870.0 1150) (list 10870.0 1175) (list 10830.0 1175) "C")
(command "_.PLINE" (list 10840.0 1150) (list 10860.0 1150) (list 10850 1140) (list 10840.0 1150) "")
(command "-LAYER" "S" "Textos" "")
(command "-COLOR" "7")
(command "-TEXT" "S" "Standard" "J" "C" (list 10850 1130) 10 0 "2xTV")
(command "-LAYER" "S" "Camaras" "")
(command "-COLOR" "1")
(command "_.PLINE" (list 10940.0 1150) (list 10960.0 1150) (list 10960.0 1165) (list 10940.0 1165) "C")
(command "_.CIRCLE" (list 10950 1157.5) 3)
(command "-LAYER" "S" "Textos" "")
(command "-COLOR" "7")
(command "-TEXT" "S" "Standard" "J" "C" (list 10950 1130) 10 0 "1xCCTV")
(command "-LAYER" "S" "Datos" "")
(command "-COLOR" "1")
(command "_.PLINE" (list 11040.0 1150) (list 11060.0 1150) (list 11050 1170) "C")
(command "-HATCH" "S" "L" "" "")
(command "-LAYER" "S" "Textos" "")
(command "-COLOR" "7")
(command "-TEXT" "S" "Standard" "J" "C" (list 11050 1130) 10 0 "10xDATO")
(command "-LAYER" "S" "APs" "")
(command "-COLOR" "3")
(command "_.PLINE" (list 10640.0 1350) (list 10660.0 1350) (list 10650 1375) (list 10640.0 1350) "")
(command "_.CIRCLE" (list 10650 1375) 10)
(command "_.CIRCLE" (list 10650 1375) 21.25)
(command "_.CIRCLE" (list 10650 1375) 30)
(command "-LAYER" "S" "Textos" "")
(command "-COLOR" "7")
(command "-TEXT" "S" "Standard" "J" "C" (list 10650 1330) 10 0 "4xAP")
(command "-LAYER" "S" "Telefonos" "")
(command "-COLOR" "4")
(command "_.PLINE" (list 10740.0 1350) (list 10760.0 1350) (list 10760.0 1380) (list 10740.0 1380) "C")
(command "_.CIRCLE" (list 10750 1387) 5)
(command "-LAYER" "S" "Textos" "")
(command "-COLOR" "7")
(command "-TEXT" "S" "Standard" "J" "C" (list 10750 1330) 10 0 "4xTEL")
(command "-LAYER" "S" "TVs" "")
(command "-COLOR" "5")
(command "_.PLINE" (list 10830.0 1350) (list 10870.0 1350) (list 10870.0 1375) (list 10830.0 1375) "C")
(command "_.PLINE" (list 10840.0 1350) (list 10860.0 1350) (list 10850 1340) (list 10840.0 1350) "")
(command "-LAYER" "S" "Textos" "")
(command "-COLOR" "7")
(command "-TEXT" "S" "Standard" "J" "C" (list 10850 1330) 10 0 "2xTV")
(command "-LAYER" "S" "Camaras" "")
(command "-COLOR" "1")
(command "_.PLINE" (list 10940.0 1350) (list 10960.0 1350) (list 10960.0 1365) (list 10940.0 1365) "C")
(command "_.CIRCLE" (list 10950 1357.5) 3)
(command "-LAYER" "S" "Textos" "")
(command "-COLOR" "7")
(command "-TEXT" "S" "Standard" "J" "C" (list 10950 1330) 10 0 "1xCCTV")
(command "-LAYER" "S" "Datos" "")
(command "-COLOR" "1")
(command "_.PLINE" (list 11040.0 1350) (list 11060.0 1350) (list 11050 1370) "C")
(command "-HATCH" "S" "L" "" "")
(command "-LAYER" "S" "Textos" "")
(command "-COLOR" "7")
(command "-TEXT" "S" "Standard" "J" "C" (list 11050 1330) 10 0 "10xDATO")
(command "-LAYER" "S" "APs" "")
(command "-COLOR" "3")
(command "_.PLINE" (list 10640.0 1550) (list 10660.0 1550) (list 10650 1575) (list 10640.0 1550) "")
(command "_.CIRCLE" (list 10650 1575) 10)
(command "_.CIRCLE" (list 10650 1575) 21.25)
(command "_.CIRCLE" (list 10650 1575) 30)
(command "-LAYER" "S" "Textos" "")
(command "-COLOR" "7")
(command "-TEXT" "S" "Standard" "J" "C" (list 10650 1530) 10 0 "2xAP")
(command "-LAYER" "S" "Telefonos" "")
(command "-COLOR" "4")
(command "_.PLINE" (list 10740.0 1550) (list 10760.0 1550) (list 10760.0 1580) (list 10740.0 1580) "C")
(command "_.CIRCLE" (list 10750 1587) 5)
(command "-LAYER" "S" "Textos" "")
(command "-COLOR" "7")
(command "-TEXT" "S" "Standard" "J" "C" (list 10750 1530) 10 0 "2xTEL")
(command "-LAYER" "S" "TVs" "")
(command "-COLOR" "5")
(command "_.PLINE" (list 10830.0 1550) (list 10870.0 1550) (list 10870.0 1575) (list 10830.0 1575) "C")
(command "_.PLINE" (list 10840.0 1550) (list 10860.0 1550) (list 10850 1540) (list 10840.0 1550) "")
(command "-LAYER" "S" "Textos" "")
(command "-COLOR" "7")
(command "-TEXT" "S" "Standard" "J" "C" (list 10850 1530) 10 0 "1xTV")
(command "-LAYER" "S" "Camaras" "")
(command "-COLOR" "1")
(command "_.PLINE" (list 10940.0 1550) (list 10960.0 1550) (list 10960.0 1565) (list 10940.0 1565) "C")
(command "_.CIRCLE" (list 10950 1557.5) 3)
(command "-LAYER" "S" "Textos" "")
(command "-COLOR" "7")
(command "-TEXT" "S" "Standard" "J" "C" (list 10950 1530) 10 0 "1xCCTV")
(command "-LAYER" "S" "Datos" "")
(command "-COLOR" "1")
(command "_.PLINE" (list 11040.0 1550) (list 11060.0 1550) (list 11050 1570) "C")
(command "-HATCH" "S" "L" "" "")
(command "-LAYER" "S" "Textos" "")
(command "-COLOR" "7")
(command "-TEXT" "S" "Standard" "J" "C" (list 11050 1530) 10 0 "6xDATO")
(princ "DONE.")

; === DIBUJAR TORRE: IDF11 ===
(princ "\n>> Dibujando Torre: IDF11...")
(command "-LAYER" "S" "Textos" "")
(command "-COLOR" "7")
(command "-TEXT" "S" "Standard" "J" "C" (list 11650 150) 25 0 "IDF11")
(princ "\n   - Dibujando switches...")
(command "-LAYER" "S" "Switches" "")
(command "-COLOR" "6")
(command "_.PLINE" (list 11700 -200) (list 11820 -200) (list 11820 -160) (list 11700 -160) "C")
(command "-LAYER" "S" "Textos" "")
(command "-COLOR" "7")
(command "-TEXT" "S" "Standard" "J" "C" (list 11705 -185) 8 0 "SW-CCTV (DS-3E3728F)")
(command "-LAYER" "S" "Switches" "")
(command "-COLOR" "6")
(command "_.PLINE" (list 11700 -140) (list 11820 -140) (list 11820 -100) (list 11700 -100) "C")
(command "-LAYER" "S" "Textos" "")
(command "-COLOR" "7")
(command "-TEXT" "S" "Standard" "J" "C" (list 11705 -125) 8 0 "SW-DATA (Meraki MS225)")
(command "-LAYER" "S" "Switches" "")
(command "-COLOR" "6")
(command "_.PLINE" (list 11700 -80) (list 11820 -80) (list 11820 -40) (list 11700 -40) "C")
(command "-LAYER" "S" "Textos" "")
(command "-COLOR" "7")
(command "-TEXT" "S" "Standard" "J" "C" (list 11705 -65) 8 0 "SW-IPTV (RG-NBS6002)")
(command "-LAYER" "S" "Switches" "")
(command "-COLOR" "6")
(command "_.PLINE" (list 11700 -20) (list 11820 -20) (list 11820 20) (list 11700 20) "C")
(command "-LAYER" "S" "Textos" "")
(command "-COLOR" "7")
(command "-TEXT" "S" "Standard" "J" "C" (list 11705 -5) 8 0 "SW-TEL (Meraki MS225)")
(command "-LAYER" "S" "Switches" "")
(command "-COLOR" "6")
(command "_.PLINE" (list 11700 40) (list 11820 40) (list 11820 80) (list 11700 80) "C")
(command "-LAYER" "S" "Textos" "")
(command "-COLOR" "7")
(command "-TEXT" "S" "Standard" "J" "C" (list 11705 55) 8 0 "SW-WIFI (Meraki MS225)")
(princ "DONE.")
(princ "\n   - Dibujando dispositivos por nivel...")
(command "-LAYER" "S" "Telefonos" "")
(command "-COLOR" "4")
(command "_.PLINE" (list 11690.0 150) (list 11710.0 150) (list 11710.0 180) (list 11690.0 180) "C")
(command "_.CIRCLE" (list 11700 187) 5)
(command "-LAYER" "S" "Textos" "")
(command "-COLOR" "7")
(command "-TEXT" "S" "Standard" "J" "C" (list 11700 130) 10 0 "1xTEL")
(command "-LAYER" "S" "Camaras" "")
(command "-COLOR" "1")
(command "_.PLINE" (list 11790.0 150) (list 11810.0 150) (list 11810.0 165) (list 11790.0 165) "C")
(command "_.CIRCLE" (list 11800 157.5) 3)
(command "-LAYER" "S" "Textos" "")
(command "-COLOR" "7")
(command "-TEXT" "S" "Standard" "J" "C" (list 11800 130) 10 0 "1xCCTV")
(command "-LAYER" "S" "Datos" "")
(command "-COLOR" "1")
(command "_.PLINE" (list 11890.0 150) (list 11910.0 150) (list 11900 170) "C")
(command "-HATCH" "S" "L" "" "")
(command "-LAYER" "S" "Textos" "")
(command "-COLOR" "7")
(command "-TEXT" "S" "Standard" "J" "C" (list 11900 130) 10 0 "3xDATO")
(command "-LAYER" "S" "APs" "")
(command "-COLOR" "3")
(command "_.PLINE" (list 11690.0 350) (list 11710.0 350) (list 11700 375) (list 11690.0 350) "")
(command "_.CIRCLE" (list 11700 375) 10)
(command "_.CIRCLE" (list 11700 375) 21.25)
(command "_.CIRCLE" (list 11700 375) 30)
(command "-LAYER" "S" "Textos" "")
(command "-COLOR" "7")
(command "-TEXT" "S" "Standard" "J" "C" (list 11700 330) 10 0 "5xAP")
(command "-LAYER" "S" "Telefonos" "")
(command "-COLOR" "4")
(command "_.PLINE" (list 11790.0 350) (list 11810.0 350) (list 11810.0 380) (list 11790.0 380) "C")
(command "_.CIRCLE" (list 11800 387) 5)
(command "-LAYER" "S" "Textos" "")
(command "-COLOR" "7")
(command "-TEXT" "S" "Standard" "J" "C" (list 11800 330) 10 0 "6xTEL")
(command "-LAYER" "S" "TVs" "")
(command "-COLOR" "5")
(command "_.PLINE" (list 11880.0 350) (list 11920.0 350) (list 11920.0 375) (list 11880.0 375) "C")
(command "_.PLINE" (list 11890.0 350) (list 11910.0 350) (list 11900 340) (list 11890.0 350) "")
(command "-LAYER" "S" "Textos" "")
(command "-COLOR" "7")
(command "-TEXT" "S" "Standard" "J" "C" (list 11900 330) 10 0 "4xTV")
(command "-LAYER" "S" "Camaras" "")
(command "-COLOR" "1")
(command "_.PLINE" (list 11990.0 350) (list 12010.0 350) (list 12010.0 365) (list 11990.0 365) "C")
(command "_.CIRCLE" (list 12000 357.5) 3)
(command "-LAYER" "S" "Textos" "")
(command "-COLOR" "7")
(command "-TEXT" "S" "Standard" "J" "C" (list 12000 330) 10 0 "2xCCTV")
(command "-LAYER" "S" "Datos" "")
(command "-COLOR" "1")
(command "_.PLINE" (list 12090.0 350) (list 12110.0 350) (list 12100 370) "C")
(command "-HATCH" "S" "L" "" "")
(command "-LAYER" "S" "Textos" "")
(command "-COLOR" "7")
(command "-TEXT" "S" "Standard" "J" "C" (list 12100 330) 10 0 "14xDATO")
(command "-LAYER" "S" "APs" "")
(command "-COLOR" "3")
(command "_.PLINE" (list 11690.0 550) (list 11710.0 550) (list 11700 575) (list 11690.0 550) "")
(command "_.CIRCLE" (list 11700 575) 10)
(command "_.CIRCLE" (list 11700 575) 21.25)
(command "_.CIRCLE" (list 11700 575) 30)
(command "-LAYER" "S" "Textos" "")
(command "-COLOR" "7")
(command "-TEXT" "S" "Standard" "J" "C" (list 11700 530) 10 0 "4xAP")
(command "-LAYER" "S" "Telefonos" "")
(command "-COLOR" "4")
(command "_.PLINE" (list 11790.0 550) (list 11810.0 550) (list 11810.0 580) (list 11790.0 580) "C")
(command "_.CIRCLE" (list 11800 587) 5)
(command "-LAYER" "S" "Textos" "")
(command "-COLOR" "7")
(command "-TEXT" "S" "Standard" "J" "C" (list 11800 530) 10 0 "4xTEL")
(command "-LAYER" "S" "TVs" "")
(command "-COLOR" "5")
(command "_.PLINE" (list 11880.0 550) (list 11920.0 550) (list 11920.0 575) (list 11880.0 575) "C")
(command "_.PLINE" (list 11890.0 550) (list 11910.0 550) (list 11900 540) (list 11890.0 550) "")
(command "-LAYER" "S" "Textos" "")
(command "-COLOR" "7")
(command "-TEXT" "S" "Standard" "J" "C" (list 11900 530) 10 0 "2xTV")
(command "-LAYER" "S" "Camaras" "")
(command "-COLOR" "1")
(command "_.PLINE" (list 11990.0 550) (list 12010.0 550) (list 12010.0 565) (list 11990.0 565) "C")
(command "_.CIRCLE" (list 12000 557.5) 3)
(command "-LAYER" "S" "Textos" "")
(command "-COLOR" "7")
(command "-TEXT" "S" "Standard" "J" "C" (list 12000 530) 10 0 "1xCCTV")
(command "-LAYER" "S" "Datos" "")
(command "-COLOR" "1")
(command "_.PLINE" (list 12090.0 550) (list 12110.0 550) (list 12100 570) "C")
(command "-HATCH" "S" "L" "" "")
(command "-LAYER" "S" "Textos" "")
(command "-COLOR" "7")
(command "-TEXT" "S" "Standard" "J" "C" (list 12100 530) 10 0 "10xDATO")
(command "-LAYER" "S" "APs" "")
(command "-COLOR" "3")
(command "_.PLINE" (list 11690.0 750) (list 11710.0 750) (list 11700 775) (list 11690.0 750) "")
(command "_.CIRCLE" (list 11700 775) 10)
(command "_.CIRCLE" (list 11700 775) 21.25)
(command "_.CIRCLE" (list 11700 775) 30)
(command "-LAYER" "S" "Textos" "")
(command "-COLOR" "7")
(command "-TEXT" "S" "Standard" "J" "C" (list 11700 730) 10 0 "4xAP")
(command "-LAYER" "S" "Telefonos" "")
(command "-COLOR" "4")
(command "_.PLINE" (list 11790.0 750) (list 11810.0 750) (list 11810.0 780) (list 11790.0 780) "C")
(command "_.CIRCLE" (list 11800 787) 5)
(command "-LAYER" "S" "Textos" "")
(command "-COLOR" "7")
(command "-TEXT" "S" "Standard" "J" "C" (list 11800 730) 10 0 "4xTEL")
(command "-LAYER" "S" "TVs" "")
(command "-COLOR" "5")
(command "_.PLINE" (list 11880.0 750) (list 11920.0 750) (list 11920.0 775) (list 11880.0 775) "C")
(command "_.PLINE" (list 11890.0 750) (list 11910.0 750) (list 11900 740) (list 11890.0 750) "")
(command "-LAYER" "S" "Textos" "")
(command "-COLOR" "7")
(command "-TEXT" "S" "Standard" "J" "C" (list 11900 730) 10 0 "2xTV")
(command "-LAYER" "S" "Camaras" "")
(command "-COLOR" "1")
(command "_.PLINE" (list 11990.0 750) (list 12010.0 750) (list 12010.0 765) (list 11990.0 765) "C")
(command "_.CIRCLE" (list 12000 757.5) 3)
(command "-LAYER" "S" "Textos" "")
(command "-COLOR" "7")
(command "-TEXT" "S" "Standard" "J" "C" (list 12000 730) 10 0 "1xCCTV")
(command "-LAYER" "S" "Datos" "")
(command "-COLOR" "1")
(command "_.PLINE" (list 12090.0 750) (list 12110.0 750) (list 12100 770) "C")
(command "-HATCH" "S" "L" "" "")
(command "-LAYER" "S" "Textos" "")
(command "-COLOR" "7")
(command "-TEXT" "S" "Standard" "J" "C" (list 12100 730) 10 0 "10xDATO")
(command "-LAYER" "S" "APs" "")
(command "-COLOR" "3")
(command "_.PLINE" (list 11690.0 950) (list 11710.0 950) (list 11700 975) (list 11690.0 950) "")
(command "_.CIRCLE" (list 11700 975) 10)
(command "_.CIRCLE" (list 11700 975) 21.25)
(command "_.CIRCLE" (list 11700 975) 30)
(command "-LAYER" "S" "Textos" "")
(command "-COLOR" "7")
(command "-TEXT" "S" "Standard" "J" "C" (list 11700 930) 10 0 "4xAP")
(command "-LAYER" "S" "Telefonos" "")
(command "-COLOR" "4")
(command "_.PLINE" (list 11790.0 950) (list 11810.0 950) (list 11810.0 980) (list 11790.0 980) "C")
(command "_.CIRCLE" (list 11800 987) 5)
(command "-LAYER" "S" "Textos" "")
(command "-COLOR" "7")
(command "-TEXT" "S" "Standard" "J" "C" (list 11800 930) 10 0 "4xTEL")
(command "-LAYER" "S" "TVs" "")
(command "-COLOR" "5")
(command "_.PLINE" (list 11880.0 950) (list 11920.0 950) (list 11920.0 975) (list 11880.0 975) "C")
(command "_.PLINE" (list 11890.0 950) (list 11910.0 950) (list 11900 940) (list 11890.0 950) "")
(command "-LAYER" "S" "Textos" "")
(command "-COLOR" "7")
(command "-TEXT" "S" "Standard" "J" "C" (list 11900 930) 10 0 "2xTV")
(command "-LAYER" "S" "Camaras" "")
(command "-COLOR" "1")
(command "_.PLINE" (list 11990.0 950) (list 12010.0 950) (list 12010.0 965) (list 11990.0 965) "C")
(command "_.CIRCLE" (list 12000 957.5) 3)
(command "-LAYER" "S" "Textos" "")
(command "-COLOR" "7")
(command "-TEXT" "S" "Standard" "J" "C" (list 12000 930) 10 0 "1xCCTV")
(command "-LAYER" "S" "Datos" "")
(command "-COLOR" "1")
(command "_.PLINE" (list 12090.0 950) (list 12110.0 950) (list 12100 970) "C")
(command "-HATCH" "S" "L" "" "")
(command "-LAYER" "S" "Textos" "")
(command "-COLOR" "7")
(command "-TEXT" "S" "Standard" "J" "C" (list 12100 930) 10 0 "10xDATO")
(command "-LAYER" "S" "APs" "")
(command "-COLOR" "3")
(command "_.PLINE" (list 11690.0 1150) (list 11710.0 1150) (list 11700 1175) (list 11690.0 1150) "")
(command "_.CIRCLE" (list 11700 1175) 10)
(command "_.CIRCLE" (list 11700 1175) 21.25)
(command "_.CIRCLE" (list 11700 1175) 30)
(command "-LAYER" "S" "Textos" "")
(command "-COLOR" "7")
(command "-TEXT" "S" "Standard" "J" "C" (list 11700 1130) 10 0 "4xAP")
(command "-LAYER" "S" "Telefonos" "")
(command "-COLOR" "4")
(command "_.PLINE" (list 11790.0 1150) (list 11810.0 1150) (list 11810.0 1180) (list 11790.0 1180) "C")
(command "_.CIRCLE" (list 11800 1187) 5)
(command "-LAYER" "S" "Textos" "")
(command "-COLOR" "7")
(command "-TEXT" "S" "Standard" "J" "C" (list 11800 1130) 10 0 "4xTEL")
(command "-LAYER" "S" "TVs" "")
(command "-COLOR" "5")
(command "_.PLINE" (list 11880.0 1150) (list 11920.0 1150) (list 11920.0 1175) (list 11880.0 1175) "C")
(command "_.PLINE" (list 11890.0 1150) (list 11910.0 1150) (list 11900 1140) (list 11890.0 1150) "")
(command "-LAYER" "S" "Textos" "")
(command "-COLOR" "7")
(command "-TEXT" "S" "Standard" "J" "C" (list 11900 1130) 10 0 "2xTV")
(command "-LAYER" "S" "Camaras" "")
(command "-COLOR" "1")
(command "_.PLINE" (list 11990.0 1150) (list 12010.0 1150) (list 12010.0 1165) (list 11990.0 1165) "C")
(command "_.CIRCLE" (list 12000 1157.5) 3)
(command "-LAYER" "S" "Textos" "")
(command "-COLOR" "7")
(command "-TEXT" "S" "Standard" "J" "C" (list 12000 1130) 10 0 "1xCCTV")
(command "-LAYER" "S" "Datos" "")
(command "-COLOR" "1")
(command "_.PLINE" (list 12090.0 1150) (list 12110.0 1150) (list 12100 1170) "C")
(command "-HATCH" "S" "L" "" "")
(command "-LAYER" "S" "Textos" "")
(command "-COLOR" "7")
(command "-TEXT" "S" "Standard" "J" "C" (list 12100 1130) 10 0 "10xDATO")
(command "-LAYER" "S" "APs" "")
(command "-COLOR" "3")
(command "_.PLINE" (list 11690.0 1350) (list 11710.0 1350) (list 11700 1375) (list 11690.0 1350) "")
(command "_.CIRCLE" (list 11700 1375) 10)
(command "_.CIRCLE" (list 11700 1375) 21.25)
(command "_.CIRCLE" (list 11700 1375) 30)
(command "-LAYER" "S" "Textos" "")
(command "-COLOR" "7")
(command "-TEXT" "S" "Standard" "J" "C" (list 11700 1330) 10 0 "4xAP")
(command "-LAYER" "S" "Telefonos" "")
(command "-COLOR" "4")
(command "_.PLINE" (list 11790.0 1350) (list 11810.0 1350) (list 11810.0 1380) (list 11790.0 1380) "C")
(command "_.CIRCLE" (list 11800 1387) 5)
(command "-LAYER" "S" "Textos" "")
(command "-COLOR" "7")
(command "-TEXT" "S" "Standard" "J" "C" (list 11800 1330) 10 0 "4xTEL")
(command "-LAYER" "S" "TVs" "")
(command "-COLOR" "5")
(command "_.PLINE" (list 11880.0 1350) (list 11920.0 1350) (list 11920.0 1375) (list 11880.0 1375) "C")
(command "_.PLINE" (list 11890.0 1350) (list 11910.0 1350) (list 11900 1340) (list 11890.0 1350) "")
(command "-LAYER" "S" "Textos" "")
(command "-COLOR" "7")
(command "-TEXT" "S" "Standard" "J" "C" (list 11900 1330) 10 0 "2xTV")
(command "-LAYER" "S" "Camaras" "")
(command "-COLOR" "1")
(command "_.PLINE" (list 11990.0 1350) (list 12010.0 1350) (list 12010.0 1365) (list 11990.0 1365) "C")
(command "_.CIRCLE" (list 12000 1357.5) 3)
(command "-LAYER" "S" "Textos" "")
(command "-COLOR" "7")
(command "-TEXT" "S" "Standard" "J" "C" (list 12000 1330) 10 0 "1xCCTV")
(command "-LAYER" "S" "Datos" "")
(command "-COLOR" "1")
(command "_.PLINE" (list 12090.0 1350) (list 12110.0 1350) (list 12100 1370) "C")
(command "-HATCH" "S" "L" "" "")
(command "-LAYER" "S" "Textos" "")
(command "-COLOR" "7")
(command "-TEXT" "S" "Standard" "J" "C" (list 12100 1330) 10 0 "10xDATO")
(command "-LAYER" "S" "APs" "")
(command "-COLOR" "3")
(command "_.PLINE" (list 11690.0 1550) (list 11710.0 1550) (list 11700 1575) (list 11690.0 1550) "")
(command "_.CIRCLE" (list 11700 1575) 10)
(command "_.CIRCLE" (list 11700 1575) 21.25)
(command "_.CIRCLE" (list 11700 1575) 30)
(command "-LAYER" "S" "Textos" "")
(command "-COLOR" "7")
(command "-TEXT" "S" "Standard" "J" "C" (list 11700 1530) 10 0 "2xAP")
(command "-LAYER" "S" "Telefonos" "")
(command "-COLOR" "4")
(command "_.PLINE" (list 11790.0 1550) (list 11810.0 1550) (list 11810.0 1580) (list 11790.0 1580) "C")
(command "_.CIRCLE" (list 11800 1587) 5)
(command "-LAYER" "S" "Textos" "")
(command "-COLOR" "7")
(command "-TEXT" "S" "Standard" "J" "C" (list 11800 1530) 10 0 "2xTEL")
(command "-LAYER" "S" "TVs" "")
(command "-COLOR" "5")
(command "_.PLINE" (list 11880.0 1550) (list 11920.0 1550) (list 11920.0 1575) (list 11880.0 1575) "C")
(command "_.PLINE" (list 11890.0 1550) (list 11910.0 1550) (list 11900 1540) (list 11890.0 1550) "")
(command "-LAYER" "S" "Textos" "")
(command "-COLOR" "7")
(command "-TEXT" "S" "Standard" "J" "C" (list 11900 1530) 10 0 "1xTV")
(command "-LAYER" "S" "Camaras" "")
(command "-COLOR" "1")
(command "_.PLINE" (list 11990.0 1550) (list 12010.0 1550) (list 12010.0 1565) (list 11990.0 1565) "C")
(command "_.CIRCLE" (list 12000 1557.5) 3)
(command "-LAYER" "S" "Textos" "")
(command "-COLOR" "7")
(command "-TEXT" "S" "Standard" "J" "C" (list 12000 1530) 10 0 "1xCCTV")
(command "-LAYER" "S" "Datos" "")
(command "-COLOR" "1")
(command "_.PLINE" (list 12090.0 1550) (list 12110.0 1550) (list 12100 1570) "C")
(command "-HATCH" "S" "L" "" "")
(command "-LAYER" "S" "Textos" "")
(command "-COLOR" "7")
(command "-TEXT" "S" "Standard" "J" "C" (list 12100 1530) 10 0 "6xDATO")
(princ "DONE.")

; === DIBUJAR TORRE: IDF12 ===
(princ "\n>> Dibujando Torre: IDF12...")
(command "-LAYER" "S" "Textos" "")
(command "-COLOR" "7")
(command "-TEXT" "S" "Standard" "J" "C" (list 12700 150) 25 0 "IDF12")
(princ "\n   - Dibujando switches...")
(command "-LAYER" "S" "Switches" "")
(command "-COLOR" "6")
(command "_.PLINE" (list 12750 -200) (list 12870 -200) (list 12870 -160) (list 12750 -160) "C")
(command "-LAYER" "S" "Textos" "")
(command "-COLOR" "7")
(command "-TEXT" "S" "Standard" "J" "C" (list 12755 -185) 8 0 "SW-CCTV (DS-3E3728F)")
(command "-LAYER" "S" "Switches" "")
(command "-COLOR" "6")
(command "_.PLINE" (list 12750 -140) (list 12870 -140) (list 12870 -100) (list 12750 -100) "C")
(command "-LAYER" "S" "Textos" "")
(command "-COLOR" "7")
(command "-TEXT" "S" "Standard" "J" "C" (list 12755 -125) 8 0 "SW-DATA (Meraki MS225)")
(command "-LAYER" "S" "Switches" "")
(command "-COLOR" "6")
(command "_.PLINE" (list 12750 -80) (list 12870 -80) (list 12870 -40) (list 12750 -40) "C")
(command "-LAYER" "S" "Textos" "")
(command "-COLOR" "7")
(command "-TEXT" "S" "Standard" "J" "C" (list 12755 -65) 8 0 "SW-IPTV (RG-NBS6002)")
(command "-LAYER" "S" "Switches" "")
(command "-COLOR" "6")
(command "_.PLINE" (list 12750 -20) (list 12870 -20) (list 12870 20) (list 12750 20) "C")
(command "-LAYER" "S" "Textos" "")
(command "-COLOR" "7")
(command "-TEXT" "S" "Standard" "J" "C" (list 12755 -5) 8 0 "SW-TEL (Meraki MS225)")
(command "-LAYER" "S" "Switches" "")
(command "-COLOR" "6")
(command "_.PLINE" (list 12750 40) (list 12870 40) (list 12870 80) (list 12750 80) "C")
(command "-LAYER" "S" "Textos" "")
(command "-COLOR" "7")
(command "-TEXT" "S" "Standard" "J" "C" (list 12755 55) 8 0 "SW-WIFI (Meraki MS225)")
(princ "DONE.")
(princ "\n   - Dibujando dispositivos por nivel...")
(command "-LAYER" "S" "APs" "")
(command "-COLOR" "3")
(command "_.PLINE" (list 12740.0 150) (list 12760.0 150) (list 12750 175) (list 12740.0 150) "")
(command "_.CIRCLE" (list 12750 175) 10)
(command "_.CIRCLE" (list 12750 175) 21.25)
(command "_.CIRCLE" (list 12750 175) 30)
(command "-LAYER" "S" "Textos" "")
(command "-COLOR" "7")
(command "-TEXT" "S" "Standard" "J" "C" (list 12750 130) 10 0 "2xAP")
(command "-LAYER" "S" "Telefonos" "")
(command "-COLOR" "4")
(command "_.PLINE" (list 12840.0 150) (list 12860.0 150) (list 12860.0 180) (list 12840.0 180) "C")
(command "_.CIRCLE" (list 12850 187) 5)
(command "-LAYER" "S" "Textos" "")
(command "-COLOR" "7")
(command "-TEXT" "S" "Standard" "J" "C" (list 12850 130) 10 0 "3xTEL")
(command "-LAYER" "S" "TVs" "")
(command "-COLOR" "5")
(command "_.PLINE" (list 12930.0 150) (list 12970.0 150) (list 12970.0 175) (list 12930.0 175) "C")
(command "_.PLINE" (list 12940.0 150) (list 12960.0 150) (list 12950 140) (list 12940.0 150) "")
(command "-LAYER" "S" "Textos" "")
(command "-COLOR" "7")
(command "-TEXT" "S" "Standard" "J" "C" (list 12950 130) 10 0 "2xTV")
(command "-LAYER" "S" "Camaras" "")
(command "-COLOR" "1")
(command "_.PLINE" (list 13040.0 150) (list 13060.0 150) (list 13060.0 165) (list 13040.0 165) "C")
(command "_.CIRCLE" (list 13050 157.5) 3)
(command "-LAYER" "S" "Textos" "")
(command "-COLOR" "7")
(command "-TEXT" "S" "Standard" "J" "C" (list 13050 130) 10 0 "1xCCTV")
(command "-LAYER" "S" "Datos" "")
(command "-COLOR" "1")
(command "_.PLINE" (list 13140.0 150) (list 13160.0 150) (list 13150 170) "C")
(command "-HATCH" "S" "L" "" "")
(command "-LAYER" "S" "Textos" "")
(command "-COLOR" "7")
(command "-TEXT" "S" "Standard" "J" "C" (list 13150 130) 10 0 "7xDATO")
(command "-LAYER" "S" "APs" "")
(command "-COLOR" "3")
(command "_.PLINE" (list 12740.0 350) (list 12760.0 350) (list 12750 375) (list 12740.0 350) "")
(command "_.CIRCLE" (list 12750 375) 10)
(command "_.CIRCLE" (list 12750 375) 21.25)
(command "_.CIRCLE" (list 12750 375) 30)
(command "-LAYER" "S" "Textos" "")
(command "-COLOR" "7")
(command "-TEXT" "S" "Standard" "J" "C" (list 12750 330) 10 0 "4xAP")
(command "-LAYER" "S" "Telefonos" "")
(command "-COLOR" "4")
(command "_.PLINE" (list 12840.0 350) (list 12860.0 350) (list 12860.0 380) (list 12840.0 380) "C")
(command "_.CIRCLE" (list 12850 387) 5)
(command "-LAYER" "S" "Textos" "")
(command "-COLOR" "7")
(command "-TEXT" "S" "Standard" "J" "C" (list 12850 330) 10 0 "5xTEL")
(command "-LAYER" "S" "TVs" "")
(command "-COLOR" "5")
(command "_.PLINE" (list 12930.0 350) (list 12970.0 350) (list 12970.0 375) (list 12930.0 375) "C")
(command "_.PLINE" (list 12940.0 350) (list 12960.0 350) (list 12950 340) (list 12940.0 350) "")
(command "-LAYER" "S" "Textos" "")
(command "-COLOR" "7")
(command "-TEXT" "S" "Standard" "J" "C" (list 12950 330) 10 0 "3xTV")
(command "-LAYER" "S" "Camaras" "")
(command "-COLOR" "1")
(command "_.PLINE" (list 13040.0 350) (list 13060.0 350) (list 13060.0 365) (list 13040.0 365) "C")
(command "_.CIRCLE" (list 13050 357.5) 3)
(command "-LAYER" "S" "Textos" "")
(command "-COLOR" "7")
(command "-TEXT" "S" "Standard" "J" "C" (list 13050 330) 10 0 "2xCCTV")
(command "-LAYER" "S" "Datos" "")
(command "-COLOR" "1")
(command "_.PLINE" (list 13140.0 350) (list 13160.0 350) (list 13150 370) "C")
(command "-HATCH" "S" "L" "" "")
(command "-LAYER" "S" "Textos" "")
(command "-COLOR" "7")
(command "-TEXT" "S" "Standard" "J" "C" (list 13150 330) 10 0 "12xDATO")
(command "-LAYER" "S" "APs" "")
(command "-COLOR" "3")
(command "_.PLINE" (list 12740.0 550) (list 12760.0 550) (list 12750 575) (list 12740.0 550) "")
(command "_.CIRCLE" (list 12750 575) 10)
(command "_.CIRCLE" (list 12750 575) 21.25)
(command "_.CIRCLE" (list 12750 575) 30)
(command "-LAYER" "S" "Textos" "")
(command "-COLOR" "7")
(command "-TEXT" "S" "Standard" "J" "C" (list 12750 530) 10 0 "4xAP")
(command "-LAYER" "S" "Telefonos" "")
(command "-COLOR" "4")
(command "_.PLINE" (list 12840.0 550) (list 12860.0 550) (list 12860.0 580) (list 12840.0 580) "C")
(command "_.CIRCLE" (list 12850 587) 5)
(command "-LAYER" "S" "Textos" "")
(command "-COLOR" "7")
(command "-TEXT" "S" "Standard" "J" "C" (list 12850 530) 10 0 "4xTEL")
(command "-LAYER" "S" "TVs" "")
(command "-COLOR" "5")
(command "_.PLINE" (list 12930.0 550) (list 12970.0 550) (list 12970.0 575) (list 12930.0 575) "C")
(command "_.PLINE" (list 12940.0 550) (list 12960.0 550) (list 12950 540) (list 12940.0 550) "")
(command "-LAYER" "S" "Textos" "")
(command "-COLOR" "7")
(command "-TEXT" "S" "Standard" "J" "C" (list 12950 530) 10 0 "2xTV")
(command "-LAYER" "S" "Camaras" "")
(command "-COLOR" "1")
(command "_.PLINE" (list 13040.0 550) (list 13060.0 550) (list 13060.0 565) (list 13040.0 565) "C")
(command "_.CIRCLE" (list 13050 557.5) 3)
(command "-LAYER" "S" "Textos" "")
(command "-COLOR" "7")
(command "-TEXT" "S" "Standard" "J" "C" (list 13050 530) 10 0 "1xCCTV")
(command "-LAYER" "S" "Datos" "")
(command "-COLOR" "1")
(command "_.PLINE" (list 13140.0 550) (list 13160.0 550) (list 13150 570) "C")
(command "-HATCH" "S" "L" "" "")
(command "-LAYER" "S" "Textos" "")
(command "-COLOR" "7")
(command "-TEXT" "S" "Standard" "J" "C" (list 13150 530) 10 0 "10xDATO")
(command "-LAYER" "S" "APs" "")
(command "-COLOR" "3")
(command "_.PLINE" (list 12740.0 750) (list 12760.0 750) (list 12750 775) (list 12740.0 750) "")
(command "_.CIRCLE" (list 12750 775) 10)
(command "_.CIRCLE" (list 12750 775) 21.25)
(command "_.CIRCLE" (list 12750 775) 30)
(command "-LAYER" "S" "Textos" "")
(command "-COLOR" "7")
(command "-TEXT" "S" "Standard" "J" "C" (list 12750 730) 10 0 "4xAP")
(command "-LAYER" "S" "Telefonos" "")
(command "-COLOR" "4")
(command "_.PLINE" (list 12840.0 750) (list 12860.0 750) (list 12860.0 780) (list 12840.0 780) "C")
(command "_.CIRCLE" (list 12850 787) 5)
(command "-LAYER" "S" "Textos" "")
(command "-COLOR" "7")
(command "-TEXT" "S" "Standard" "J" "C" (list 12850 730) 10 0 "4xTEL")
(command "-LAYER" "S" "TVs" "")
(command "-COLOR" "5")
(command "_.PLINE" (list 12930.0 750) (list 12970.0 750) (list 12970.0 775) (list 12930.0 775) "C")
(command "_.PLINE" (list 12940.0 750) (list 12960.0 750) (list 12950 740) (list 12940.0 750) "")
(command "-LAYER" "S" "Textos" "")
(command "-COLOR" "7")
(command "-TEXT" "S" "Standard" "J" "C" (list 12950 730) 10 0 "2xTV")
(command "-LAYER" "S" "Camaras" "")
(command "-COLOR" "1")
(command "_.PLINE" (list 13040.0 750) (list 13060.0 750) (list 13060.0 765) (list 13040.0 765) "C")
(command "_.CIRCLE" (list 13050 757.5) 3)
(command "-LAYER" "S" "Textos" "")
(command "-COLOR" "7")
(command "-TEXT" "S" "Standard" "J" "C" (list 13050 730) 10 0 "1xCCTV")
(command "-LAYER" "S" "Datos" "")
(command "-COLOR" "1")
(command "_.PLINE" (list 13140.0 750) (list 13160.0 750) (list 13150 770) "C")
(command "-HATCH" "S" "L" "" "")
(command "-LAYER" "S" "Textos" "")
(command "-COLOR" "7")
(command "-TEXT" "S" "Standard" "J" "C" (list 13150 730) 10 0 "10xDATO")
(command "-LAYER" "S" "APs" "")
(command "-COLOR" "3")
(command "_.PLINE" (list 12740.0 950) (list 12760.0 950) (list 12750 975) (list 12740.0 950) "")
(command "_.CIRCLE" (list 12750 975) 10)
(command "_.CIRCLE" (list 12750 975) 21.25)
(command "_.CIRCLE" (list 12750 975) 30)
(command "-LAYER" "S" "Textos" "")
(command "-COLOR" "7")
(command "-TEXT" "S" "Standard" "J" "C" (list 12750 930) 10 0 "4xAP")
(command "-LAYER" "S" "Telefonos" "")
(command "-COLOR" "4")
(command "_.PLINE" (list 12840.0 950) (list 12860.0 950) (list 12860.0 980) (list 12840.0 980) "C")
(command "_.CIRCLE" (list 12850 987) 5)
(command "-LAYER" "S" "Textos" "")
(command "-COLOR" "7")
(command "-TEXT" "S" "Standard" "J" "C" (list 12850 930) 10 0 "4xTEL")
(command "-LAYER" "S" "TVs" "")
(command "-COLOR" "5")
(command "_.PLINE" (list 12930.0 950) (list 12970.0 950) (list 12970.0 975) (list 12930.0 975) "C")
(command "_.PLINE" (list 12940.0 950) (list 12960.0 950) (list 12950 940) (list 12940.0 950) "")
(command "-LAYER" "S" "Textos" "")
(command "-COLOR" "7")
(command "-TEXT" "S" "Standard" "J" "C" (list 12950 930) 10 0 "2xTV")
(command "-LAYER" "S" "Camaras" "")
(command "-COLOR" "1")
(command "_.PLINE" (list 13040.0 950) (list 13060.0 950) (list 13060.0 965) (list 13040.0 965) "C")
(command "_.CIRCLE" (list 13050 957.5) 3)
(command "-LAYER" "S" "Textos" "")
(command "-COLOR" "7")
(command "-TEXT" "S" "Standard" "J" "C" (list 13050 930) 10 0 "1xCCTV")
(command "-LAYER" "S" "Datos" "")
(command "-COLOR" "1")
(command "_.PLINE" (list 13140.0 950) (list 13160.0 950) (list 13150 970) "C")
(command "-HATCH" "S" "L" "" "")
(command "-LAYER" "S" "Textos" "")
(command "-COLOR" "7")
(command "-TEXT" "S" "Standard" "J" "C" (list 13150 930) 10 0 "10xDATO")
(command "-LAYER" "S" "APs" "")
(command "-COLOR" "3")
(command "_.PLINE" (list 12740.0 1150) (list 12760.0 1150) (list 12750 1175) (list 12740.0 1150) "")
(command "_.CIRCLE" (list 12750 1175) 10)
(command "_.CIRCLE" (list 12750 1175) 21.25)
(command "_.CIRCLE" (list 12750 1175) 30)
(command "-LAYER" "S" "Textos" "")
(command "-COLOR" "7")
(command "-TEXT" "S" "Standard" "J" "C" (list 12750 1130) 10 0 "4xAP")
(command "-LAYER" "S" "Telefonos" "")
(command "-COLOR" "4")
(command "_.PLINE" (list 12840.0 1150) (list 12860.0 1150) (list 12860.0 1180) (list 12840.0 1180) "C")
(command "_.CIRCLE" (list 12850 1187) 5)
(command "-LAYER" "S" "Textos" "")
(command "-COLOR" "7")
(command "-TEXT" "S" "Standard" "J" "C" (list 12850 1130) 10 0 "4xTEL")
(command "-LAYER" "S" "TVs" "")
(command "-COLOR" "5")
(command "_.PLINE" (list 12930.0 1150) (list 12970.0 1150) (list 12970.0 1175) (list 12930.0 1175) "C")
(command "_.PLINE" (list 12940.0 1150) (list 12960.0 1150) (list 12950 1140) (list 12940.0 1150) "")
(command "-LAYER" "S" "Textos" "")
(command "-COLOR" "7")
(command "-TEXT" "S" "Standard" "J" "C" (list 12950 1130) 10 0 "2xTV")
(command "-LAYER" "S" "Camaras" "")
(command "-COLOR" "1")
(command "_.PLINE" (list 13040.0 1150) (list 13060.0 1150) (list 13060.0 1165) (list 13040.0 1165) "C")
(command "_.CIRCLE" (list 13050 1157.5) 3)
(command "-LAYER" "S" "Textos" "")
(command "-COLOR" "7")
(command "-TEXT" "S" "Standard" "J" "C" (list 13050 1130) 10 0 "1xCCTV")
(command "-LAYER" "S" "Datos" "")
(command "-COLOR" "1")
(command "_.PLINE" (list 13140.0 1150) (list 13160.0 1150) (list 13150 1170) "C")
(command "-HATCH" "S" "L" "" "")
(command "-LAYER" "S" "Textos" "")
(command "-COLOR" "7")
(command "-TEXT" "S" "Standard" "J" "C" (list 13150 1130) 10 0 "10xDATO")
(command "-LAYER" "S" "APs" "")
(command "-COLOR" "3")
(command "_.PLINE" (list 12740.0 1350) (list 12760.0 1350) (list 12750 1375) (list 12740.0 1350) "")
(command "_.CIRCLE" (list 12750 1375) 10)
(command "_.CIRCLE" (list 12750 1375) 21.25)
(command "_.CIRCLE" (list 12750 1375) 30)
(command "-LAYER" "S" "Textos" "")
(command "-COLOR" "7")
(command "-TEXT" "S" "Standard" "J" "C" (list 12750 1330) 10 0 "4xAP")
(command "-LAYER" "S" "Telefonos" "")
(command "-COLOR" "4")
(command "_.PLINE" (list 12840.0 1350) (list 12860.0 1350) (list 12860.0 1380) (list 12840.0 1380) "C")
(command "_.CIRCLE" (list 12850 1387) 5)
(command "-LAYER" "S" "Textos" "")
(command "-COLOR" "7")
(command "-TEXT" "S" "Standard" "J" "C" (list 12850 1330) 10 0 "4xTEL")
(command "-LAYER" "S" "TVs" "")
(command "-COLOR" "5")
(command "_.PLINE" (list 12930.0 1350) (list 12970.0 1350) (list 12970.0 1375) (list 12930.0 1375) "C")
(command "_.PLINE" (list 12940.0 1350) (list 12960.0 1350) (list 12950 1340) (list 12940.0 1350) "")
(command "-LAYER" "S" "Textos" "")
(command "-COLOR" "7")
(command "-TEXT" "S" "Standard" "J" "C" (list 12950 1330) 10 0 "2xTV")
(command "-LAYER" "S" "Camaras" "")
(command "-COLOR" "1")
(command "_.PLINE" (list 13040.0 1350) (list 13060.0 1350) (list 13060.0 1365) (list 13040.0 1365) "C")
(command "_.CIRCLE" (list 13050 1357.5) 3)
(command "-LAYER" "S" "Textos" "")
(command "-COLOR" "7")
(command "-TEXT" "S" "Standard" "J" "C" (list 13050 1330) 10 0 "1xCCTV")
(command "-LAYER" "S" "Datos" "")
(command "-COLOR" "1")
(command "_.PLINE" (list 13140.0 1350) (list 13160.0 1350) (list 13150 1370) "C")
(command "-HATCH" "S" "L" "" "")
(command "-LAYER" "S" "Textos" "")
(command "-COLOR" "7")
(command "-TEXT" "S" "Standard" "J" "C" (list 13150 1330) 10 0 "10xDATO")
(command "-LAYER" "S" "APs" "")
(command "-COLOR" "3")
(command "_.PLINE" (list 12740.0 1550) (list 12760.0 1550) (list 12750 1575) (list 12740.0 1550) "")
(command "_.CIRCLE" (list 12750 1575) 10)
(command "_.CIRCLE" (list 12750 1575) 21.25)
(command "_.CIRCLE" (list 12750 1575) 30)
(command "-LAYER" "S" "Textos" "")
(command "-COLOR" "7")
(command "-TEXT" "S" "Standard" "J" "C" (list 12750 1530) 10 0 "2xAP")
(command "-LAYER" "S" "Telefonos" "")
(command "-COLOR" "4")
(command "_.PLINE" (list 12840.0 1550) (list 12860.0 1550) (list 12860.0 1580) (list 12840.0 1580) "C")
(command "_.CIRCLE" (list 12850 1587) 5)
(command "-LAYER" "S" "Textos" "")
(command "-COLOR" "7")
(command "-TEXT" "S" "Standard" "J" "C" (list 12850 1530) 10 0 "2xTEL")
(command "-LAYER" "S" "TVs" "")
(command "-COLOR" "5")
(command "_.PLINE" (list 12930.0 1550) (list 12970.0 1550) (list 12970.0 1575) (list 12930.0 1575) "C")
(command "_.PLINE" (list 12940.0 1550) (list 12960.0 1550) (list 12950 1540) (list 12940.0 1550) "")
(command "-LAYER" "S" "Textos" "")
(command "-COLOR" "7")
(command "-TEXT" "S" "Standard" "J" "C" (list 12950 1530) 10 0 "1xTV")
(command "-LAYER" "S" "Camaras" "")
(command "-COLOR" "1")
(command "_.PLINE" (list 13040.0 1550) (list 13060.0 1550) (list 13060.0 1565) (list 13040.0 1565) "C")
(command "_.CIRCLE" (list 13050 1557.5) 3)
(command "-LAYER" "S" "Textos" "")
(command "-COLOR" "7")
(command "-TEXT" "S" "Standard" "J" "C" (list 13050 1530) 10 0 "1xCCTV")
(command "-LAYER" "S" "Datos" "")
(command "-COLOR" "1")
(command "_.PLINE" (list 13140.0 1550) (list 13160.0 1550) (list 13150 1570) "C")
(command "-HATCH" "S" "L" "" "")
(command "-LAYER" "S" "Textos" "")
(command "-COLOR" "7")
(command "-TEXT" "S" "Standard" "J" "C" (list 13150 1530) 10 0 "6xDATO")
(princ "DONE.")

; === DIBUJAR TORRE: IDF13 RECEPCION ===
(princ "\n>> Dibujando Torre: IDF13 RECEPCION...")
(command "-LAYER" "S" "Textos" "")
(command "-COLOR" "7")
(command "-TEXT" "S" "Standard" "J" "C" (list 13750 150) 25 0 "IDF13 RECEPCION")
(princ "\n   - Dibujando switches...")
(command "-LAYER" "S" "Switches" "")
(command "-COLOR" "6")
(command "_.PLINE" (list 13800 -200) (list 13920 -200) (list 13920 -160) (list 13800 -160) "C")
(command "-LAYER" "S" "Textos" "")
(command "-COLOR" "7")
(command "-TEXT" "S" "Standard" "J" "C" (list 13805 -185) 8 0 "SW-CCTV (DS-3E3728F)")
(command "-LAYER" "S" "Switches" "")
(command "-COLOR" "6")
(command "_.PLINE" (list 13800 -140) (list 13920 -140) (list 13920 -100) (list 13800 -100) "C")
(command "-LAYER" "S" "Textos" "")
(command "-COLOR" "7")
(command "-TEXT" "S" "Standard" "J" "C" (list 13805 -125) 8 0 "SW-DATA (Meraki MS225)")
(command "-LAYER" "S" "Switches" "")
(command "-COLOR" "6")
(command "_.PLINE" (list 13800 -80) (list 13920 -80) (list 13920 -40) (list 13800 -40) "C")
(command "-LAYER" "S" "Textos" "")
(command "-COLOR" "7")
(command "-TEXT" "S" "Standard" "J" "C" (list 13805 -65) 8 0 "SW-IPTV (RG-NBS6002)")
(command "-LAYER" "S" "Switches" "")
(command "-COLOR" "6")
(command "_.PLINE" (list 13800 -20) (list 13920 -20) (list 13920 20) (list 13800 20) "C")
(command "-LAYER" "S" "Textos" "")
(command "-COLOR" "7")
(command "-TEXT" "S" "Standard" "J" "C" (list 13805 -5) 8 0 "SW-TEL (Meraki MS225)")
(command "-LAYER" "S" "Switches" "")
(command "-COLOR" "6")
(command "_.PLINE" (list 13800 40) (list 13920 40) (list 13920 80) (list 13800 80) "C")
(command "-LAYER" "S" "Textos" "")
(command "-COLOR" "7")
(command "-TEXT" "S" "Standard" "J" "C" (list 13805 55) 8 0 "SW-WIFI (Meraki MS225)")
(princ "DONE.")
(princ "\n   - Dibujando dispositivos por nivel...")
(command "-LAYER" "S" "Telefonos" "")
(command "-COLOR" "4")
(command "_.PLINE" (list 13790.0 150) (list 13810.0 150) (list 13810.0 180) (list 13790.0 180) "C")
(command "_.CIRCLE" (list 13800 187) 5)
(command "-LAYER" "S" "Textos" "")
(command "-COLOR" "7")
(command "-TEXT" "S" "Standard" "J" "C" (list 13800 130) 10 0 "2xTEL")
(command "-LAYER" "S" "TVs" "")
(command "-COLOR" "5")
(command "_.PLINE" (list 13880.0 150) (list 13920.0 150) (list 13920.0 175) (list 13880.0 175) "C")
(command "_.PLINE" (list 13890.0 150) (list 13910.0 150) (list 13900 140) (list 13890.0 150) "")
(command "-LAYER" "S" "Textos" "")
(command "-COLOR" "7")
(command "-TEXT" "S" "Standard" "J" "C" (list 13900 130) 10 0 "1xTV")
(command "-LAYER" "S" "Camaras" "")
(command "-COLOR" "1")
(command "_.PLINE" (list 13990.0 150) (list 14010.0 150) (list 14010.0 165) (list 13990.0 165) "C")
(command "_.CIRCLE" (list 14000 157.5) 3)
(command "-LAYER" "S" "Textos" "")
(command "-COLOR" "7")
(command "-TEXT" "S" "Standard" "J" "C" (list 14000 130) 10 0 "1xCCTV")
(command "-LAYER" "S" "Datos" "")
(command "-COLOR" "1")
(command "_.PLINE" (list 14090.0 150) (list 14110.0 150) (list 14100 170) "C")
(command "-HATCH" "S" "L" "" "")
(command "-LAYER" "S" "Textos" "")
(command "-COLOR" "7")
(command "-TEXT" "S" "Standard" "J" "C" (list 14100 130) 10 0 "4xDATO")
(command "-LAYER" "S" "APs" "")
(command "-COLOR" "3")
(command "_.PLINE" (list 13790.0 350) (list 13810.0 350) (list 13800 375) (list 13790.0 350) "")
(command "_.CIRCLE" (list 13800 375) 10)
(command "_.CIRCLE" (list 13800 375) 21.25)
(command "_.CIRCLE" (list 13800 375) 30)
(command "-LAYER" "S" "Textos" "")
(command "-COLOR" "7")
(command "-TEXT" "S" "Standard" "J" "C" (list 13800 330) 10 0 "9xAP")
(command "-LAYER" "S" "Telefonos" "")
(command "-COLOR" "4")
(command "_.PLINE" (list 13890.0 350) (list 13910.0 350) (list 13910.0 380) (list 13890.0 380) "C")
(command "_.CIRCLE" (list 13900 387) 5)
(command "-LAYER" "S" "Textos" "")
(command "-COLOR" "7")
(command "-TEXT" "S" "Standard" "J" "C" (list 13900 330) 10 0 "10xTEL")
(command "-LAYER" "S" "TVs" "")
(command "-COLOR" "5")
(command "_.PLINE" (list 13980.0 350) (list 14020.0 350) (list 14020.0 375) (list 13980.0 375) "C")
(command "_.PLINE" (list 13990.0 350) (list 14010.0 350) (list 14000 340) (list 13990.0 350) "")
(command "-LAYER" "S" "Textos" "")
(command "-COLOR" "7")
(command "-TEXT" "S" "Standard" "J" "C" (list 14000 330) 10 0 "6xTV")
(command "-LAYER" "S" "Camaras" "")
(command "-COLOR" "1")
(command "_.PLINE" (list 14090.0 350) (list 14110.0 350) (list 14110.0 365) (list 14090.0 365) "C")
(command "_.CIRCLE" (list 14100 357.5) 3)
(command "-LAYER" "S" "Textos" "")
(command "-COLOR" "7")
(command "-TEXT" "S" "Standard" "J" "C" (list 14100 330) 10 0 "3xCCTV")
(command "-LAYER" "S" "Datos" "")
(command "-COLOR" "1")
(command "_.PLINE" (list 14190.0 350) (list 14210.0 350) (list 14200 370) "C")
(command "-HATCH" "S" "L" "" "")
(command "-LAYER" "S" "Textos" "")
(command "-COLOR" "7")
(command "-TEXT" "S" "Standard" "J" "C" (list 14200 330) 10 0 "20xDATO")
(command "-LAYER" "S" "APs" "")
(command "-COLOR" "3")
(command "_.PLINE" (list 13790.0 550) (list 13810.0 550) (list 13800 575) (list 13790.0 550) "")
(command "_.CIRCLE" (list 13800 575) 10)
(command "_.CIRCLE" (list 13800 575) 21.25)
(command "_.CIRCLE" (list 13800 575) 30)
(command "-LAYER" "S" "Textos" "")
(command "-COLOR" "7")
(command "-TEXT" "S" "Standard" "J" "C" (list 13800 530) 10 0 "6xAP")
(command "-LAYER" "S" "Telefonos" "")
(command "-COLOR" "4")
(command "_.PLINE" (list 13890.0 550) (list 13910.0 550) (list 13910.0 580) (list 13890.0 580) "C")
(command "_.CIRCLE" (list 13900 587) 5)
(command "-LAYER" "S" "Textos" "")
(command "-COLOR" "7")
(command "-TEXT" "S" "Standard" "J" "C" (list 13900 530) 10 0 "7xTEL")
(command "-LAYER" "S" "TVs" "")
(command "-COLOR" "5")
(command "_.PLINE" (list 13980.0 550) (list 14020.0 550) (list 14020.0 575) (list 13980.0 575) "C")
(command "_.PLINE" (list 13990.0 550) (list 14010.0 550) (list 14000 540) (list 13990.0 550) "")
(command "-LAYER" "S" "Textos" "")
(command "-COLOR" "7")
(command "-TEXT" "S" "Standard" "J" "C" (list 14000 530) 10 0 "4xTV")
(command "-LAYER" "S" "Camaras" "")
(command "-COLOR" "1")
(command "_.PLINE" (list 14090.0 550) (list 14110.0 550) (list 14110.0 565) (list 14090.0 565) "C")
(command "_.CIRCLE" (list 14100 557.5) 3)
(command "-LAYER" "S" "Textos" "")
(command "-COLOR" "7")
(command "-TEXT" "S" "Standard" "J" "C" (list 14100 530) 10 0 "2xCCTV")
(command "-LAYER" "S" "Datos" "")
(command "-COLOR" "1")
(command "_.PLINE" (list 14190.0 550) (list 14210.0 550) (list 14200 570) "C")
(command "-HATCH" "S" "L" "" "")
(command "-LAYER" "S" "Textos" "")
(command "-COLOR" "7")
(command "-TEXT" "S" "Standard" "J" "C" (list 14200 530) 10 0 "15xDATO")
(command "-LAYER" "S" "APs" "")
(command "-COLOR" "3")
(command "_.PLINE" (list 13790.0 750) (list 13810.0 750) (list 13800 775) (list 13790.0 750) "")
(command "_.CIRCLE" (list 13800 775) 10)
(command "_.CIRCLE" (list 13800 775) 21.25)
(command "_.CIRCLE" (list 13800 775) 30)
(command "-LAYER" "S" "Textos" "")
(command "-COLOR" "7")
(command "-TEXT" "S" "Standard" "J" "C" (list 13800 730) 10 0 "6xAP")
(command "-LAYER" "S" "Telefonos" "")
(command "-COLOR" "4")
(command "_.PLINE" (list 13890.0 750) (list 13910.0 750) (list 13910.0 780) (list 13890.0 780) "C")
(command "_.CIRCLE" (list 13900 787) 5)
(command "-LAYER" "S" "Textos" "")
(command "-COLOR" "7")
(command "-TEXT" "S" "Standard" "J" "C" (list 13900 730) 10 0 "7xTEL")
(command "-LAYER" "S" "TVs" "")
(command "-COLOR" "5")
(command "_.PLINE" (list 13980.0 750) (list 14020.0 750) (list 14020.0 775) (list 13980.0 775) "C")
(command "_.PLINE" (list 13990.0 750) (list 14010.0 750) (list 14000 740) (list 13990.0 750) "")
(command "-LAYER" "S" "Textos" "")
(command "-COLOR" "7")
(command "-TEXT" "S" "Standard" "J" "C" (list 14000 730) 10 0 "4xTV")
(command "-LAYER" "S" "Camaras" "")
(command "-COLOR" "1")
(command "_.PLINE" (list 14090.0 750) (list 14110.0 750) (list 14110.0 765) (list 14090.0 765) "C")
(command "_.CIRCLE" (list 14100 757.5) 3)
(command "-LAYER" "S" "Textos" "")
(command "-COLOR" "7")
(command "-TEXT" "S" "Standard" "J" "C" (list 14100 730) 10 0 "2xCCTV")
(command "-LAYER" "S" "Datos" "")
(command "-COLOR" "1")
(command "_.PLINE" (list 14190.0 750) (list 14210.0 750) (list 14200 770) "C")
(command "-HATCH" "S" "L" "" "")
(command "-LAYER" "S" "Textos" "")
(command "-COLOR" "7")
(command "-TEXT" "S" "Standard" "J" "C" (list 14200 730) 10 0 "15xDATO")
(command "-LAYER" "S" "APs" "")
(command "-COLOR" "3")
(command "_.PLINE" (list 13790.0 950) (list 13810.0 950) (list 13800 975) (list 13790.0 950) "")
(command "_.CIRCLE" (list 13800 975) 10)
(command "_.CIRCLE" (list 13800 975) 21.25)
(command "_.CIRCLE" (list 13800 975) 30)
(command "-LAYER" "S" "Textos" "")
(command "-COLOR" "7")
(command "-TEXT" "S" "Standard" "J" "C" (list 13800 930) 10 0 "6xAP")
(command "-LAYER" "S" "Telefonos" "")
(command "-COLOR" "4")
(command "_.PLINE" (list 13890.0 950) (list 13910.0 950) (list 13910.0 980) (list 13890.0 980) "C")
(command "_.CIRCLE" (list 13900 987) 5)
(command "-LAYER" "S" "Textos" "")
(command "-COLOR" "7")
(command "-TEXT" "S" "Standard" "J" "C" (list 13900 930) 10 0 "7xTEL")
(command "-LAYER" "S" "TVs" "")
(command "-COLOR" "5")
(command "_.PLINE" (list 13980.0 950) (list 14020.0 950) (list 14020.0 975) (list 13980.0 975) "C")
(command "_.PLINE" (list 13990.0 950) (list 14010.0 950) (list 14000 940) (list 13990.0 950) "")
(command "-LAYER" "S" "Textos" "")
(command "-COLOR" "7")
(command "-TEXT" "S" "Standard" "J" "C" (list 14000 930) 10 0 "4xTV")
(command "-LAYER" "S" "Camaras" "")
(command "-COLOR" "1")
(command "_.PLINE" (list 14090.0 950) (list 14110.0 950) (list 14110.0 965) (list 14090.0 965) "C")
(command "_.CIRCLE" (list 14100 957.5) 3)
(command "-LAYER" "S" "Textos" "")
(command "-COLOR" "7")
(command "-TEXT" "S" "Standard" "J" "C" (list 14100 930) 10 0 "2xCCTV")
(command "-LAYER" "S" "Datos" "")
(command "-COLOR" "1")
(command "_.PLINE" (list 14190.0 950) (list 14210.0 950) (list 14200 970) "C")
(command "-HATCH" "S" "L" "" "")
(command "-LAYER" "S" "Textos" "")
(command "-COLOR" "7")
(command "-TEXT" "S" "Standard" "J" "C" (list 14200 930) 10 0 "15xDATO")
(command "-LAYER" "S" "APs" "")
(command "-COLOR" "3")
(command "_.PLINE" (list 13790.0 1150) (list 13810.0 1150) (list 13800 1175) (list 13790.0 1150) "")
(command "_.CIRCLE" (list 13800 1175) 10)
(command "_.CIRCLE" (list 13800 1175) 21.25)
(command "_.CIRCLE" (list 13800 1175) 30)
(command "-LAYER" "S" "Textos" "")
(command "-COLOR" "7")
(command "-TEXT" "S" "Standard" "J" "C" (list 13800 1130) 10 0 "6xAP")
(command "-LAYER" "S" "Telefonos" "")
(command "-COLOR" "4")
(command "_.PLINE" (list 13890.0 1150) (list 13910.0 1150) (list 13910.0 1180) (list 13890.0 1180) "C")
(command "_.CIRCLE" (list 13900 1187) 5)
(command "-LAYER" "S" "Textos" "")
(command "-COLOR" "7")
(command "-TEXT" "S" "Standard" "J" "C" (list 13900 1130) 10 0 "7xTEL")
(command "-LAYER" "S" "TVs" "")
(command "-COLOR" "5")
(command "_.PLINE" (list 13980.0 1150) (list 14020.0 1150) (list 14020.0 1175) (list 13980.0 1175) "C")
(command "_.PLINE" (list 13990.0 1150) (list 14010.0 1150) (list 14000 1140) (list 13990.0 1150) "")
(command "-LAYER" "S" "Textos" "")
(command "-COLOR" "7")
(command "-TEXT" "S" "Standard" "J" "C" (list 14000 1130) 10 0 "4xTV")
(command "-LAYER" "S" "Camaras" "")
(command "-COLOR" "1")
(command "_.PLINE" (list 14090.0 1150) (list 14110.0 1150) (list 14110.0 1165) (list 14090.0 1165) "C")
(command "_.CIRCLE" (list 14100 1157.5) 3)
(command "-LAYER" "S" "Textos" "")
(command "-COLOR" "7")
(command "-TEXT" "S" "Standard" "J" "C" (list 14100 1130) 10 0 "2xCCTV")
(command "-LAYER" "S" "Datos" "")
(command "-COLOR" "1")
(command "_.PLINE" (list 14190.0 1150) (list 14210.0 1150) (list 14200 1170) "C")
(command "-HATCH" "S" "L" "" "")
(command "-LAYER" "S" "Textos" "")
(command "-COLOR" "7")
(command "-TEXT" "S" "Standard" "J" "C" (list 14200 1130) 10 0 "15xDATO")
(command "-LAYER" "S" "APs" "")
(command "-COLOR" "3")
(command "_.PLINE" (list 13790.0 1350) (list 13810.0 1350) (list 13800 1375) (list 13790.0 1350) "")
(command "_.CIRCLE" (list 13800 1375) 10)
(command "_.CIRCLE" (list 13800 1375) 21.25)
(command "_.CIRCLE" (list 13800 1375) 30)
(command "-LAYER" "S" "Textos" "")
(command "-COLOR" "7")
(command "-TEXT" "S" "Standard" "J" "C" (list 13800 1330) 10 0 "6xAP")
(command "-LAYER" "S" "Telefonos" "")
(command "-COLOR" "4")
(command "_.PLINE" (list 13890.0 1350) (list 13910.0 1350) (list 13910.0 1380) (list 13890.0 1380) "C")
(command "_.CIRCLE" (list 13900 1387) 5)
(command "-LAYER" "S" "Textos" "")
(command "-COLOR" "7")
(command "-TEXT" "S" "Standard" "J" "C" (list 13900 1330) 10 0 "7xTEL")
(command "-LAYER" "S" "TVs" "")
(command "-COLOR" "5")
(command "_.PLINE" (list 13980.0 1350) (list 14020.0 1350) (list 14020.0 1375) (list 13980.0 1375) "C")
(command "_.PLINE" (list 13990.0 1350) (list 14010.0 1350) (list 14000 1340) (list 13990.0 1350) "")
(command "-LAYER" "S" "Textos" "")
(command "-COLOR" "7")
(command "-TEXT" "S" "Standard" "J" "C" (list 14000 1330) 10 0 "4xTV")
(command "-LAYER" "S" "Camaras" "")
(command "-COLOR" "1")
(command "_.PLINE" (list 14090.0 1350) (list 14110.0 1350) (list 14110.0 1365) (list 14090.0 1365) "C")
(command "_.CIRCLE" (list 14100 1357.5) 3)
(command "-LAYER" "S" "Textos" "")
(command "-COLOR" "7")
(command "-TEXT" "S" "Standard" "J" "C" (list 14100 1330) 10 0 "2xCCTV")
(command "-LAYER" "S" "Datos" "")
(command "-COLOR" "1")
(command "_.PLINE" (list 14190.0 1350) (list 14210.0 1350) (list 14200 1370) "C")
(command "-HATCH" "S" "L" "" "")
(command "-LAYER" "S" "Textos" "")
(command "-COLOR" "7")
(command "-TEXT" "S" "Standard" "J" "C" (list 14200 1330) 10 0 "15xDATO")
(command "-LAYER" "S" "APs" "")
(command "-COLOR" "3")
(command "_.PLINE" (list 13790.0 1550) (list 13810.0 1550) (list 13800 1575) (list 13790.0 1550) "")
(command "_.CIRCLE" (list 13800 1575) 10)
(command "_.CIRCLE" (list 13800 1575) 21.25)
(command "_.CIRCLE" (list 13800 1575) 30)
(command "-LAYER" "S" "Textos" "")
(command "-COLOR" "7")
(command "-TEXT" "S" "Standard" "J" "C" (list 13800 1530) 10 0 "3xAP")
(command "-LAYER" "S" "Telefonos" "")
(command "-COLOR" "4")
(command "_.PLINE" (list 13890.0 1550) (list 13910.0 1550) (list 13910.0 1580) (list 13890.0 1580) "C")
(command "_.CIRCLE" (list 13900 1587) 5)
(command "-LAYER" "S" "Textos" "")
(command "-COLOR" "7")
(command "-TEXT" "S" "Standard" "J" "C" (list 13900 1530) 10 0 "3xTEL")
(command "-LAYER" "S" "TVs" "")
(command "-COLOR" "5")
(command "_.PLINE" (list 13980.0 1550) (list 14020.0 1550) (list 14020.0 1575) (list 13980.0 1575) "C")
(command "_.PLINE" (list 13990.0 1550) (list 14010.0 1550) (list 14000 1540) (list 13990.0 1550) "")
(command "-LAYER" "S" "Textos" "")
(command "-COLOR" "7")
(command "-TEXT" "S" "Standard" "J" "C" (list 14000 1530) 10 0 "2xTV")
(command "-LAYER" "S" "Camaras" "")
(command "-COLOR" "1")
(command "_.PLINE" (list 14090.0 1550) (list 14110.0 1550) (list 14110.0 1565) (list 14090.0 1565) "C")
(command "_.CIRCLE" (list 14100 1557.5) 3)
(command "-LAYER" "S" "Textos" "")
(command "-COLOR" "7")
(command "-TEXT" "S" "Standard" "J" "C" (list 14100 1530) 10 0 "1xCCTV")
(command "-LAYER" "S" "Datos" "")
(command "-COLOR" "1")
(command "_.PLINE" (list 14190.0 1550) (list 14210.0 1550) (list 14200 1570) "C")
(command "-HATCH" "S" "L" "" "")
(command "-LAYER" "S" "Textos" "")
(command "-COLOR" "7")
(command "-TEXT" "S" "Standard" "J" "C" (list 14200 1530) 10 0 "8xDATO")
(princ "DONE.")

; === DIBUJAR TORRE: IDF14 GYM ===
(princ "\n>> Dibujando Torre: IDF14 GYM...")
(command "-LAYER" "S" "Textos" "")
(command "-COLOR" "7")
(command "-TEXT" "S" "Standard" "J" "C" (list 14800 150) 25 0 "IDF14 GYM")
(princ "\n   - Dibujando switches...")
(command "-LAYER" "S" "Switches" "")
(command "-COLOR" "6")
(command "_.PLINE" (list 14850 -200) (list 14970 -200) (list 14970 -160) (list 14850 -160) "C")
(command "-LAYER" "S" "Textos" "")
(command "-COLOR" "7")
(command "-TEXT" "S" "Standard" "J" "C" (list 14855 -185) 8 0 "SW-CCTV (DS-3E3728F)")
(command "-LAYER" "S" "Switches" "")
(command "-COLOR" "6")
(command "_.PLINE" (list 14850 -140) (list 14970 -140) (list 14970 -100) (list 14850 -100) "C")
(command "-LAYER" "S" "Textos" "")
(command "-COLOR" "7")
(command "-TEXT" "S" "Standard" "J" "C" (list 14855 -125) 8 0 "SW-DATA (Meraki MS225)")
(command "-LAYER" "S" "Switches" "")
(command "-COLOR" "6")
(command "_.PLINE" (list 14850 -80) (list 14970 -80) (list 14970 -40) (list 14850 -40) "C")
(command "-LAYER" "S" "Textos" "")
(command "-COLOR" "7")
(command "-TEXT" "S" "Standard" "J" "C" (list 14855 -65) 8 0 "SW-IPTV (RG-NBS6002)")
(command "-LAYER" "S" "Switches" "")
(command "-COLOR" "6")
(command "_.PLINE" (list 14850 -20) (list 14970 -20) (list 14970 20) (list 14850 20) "C")
(command "-LAYER" "S" "Textos" "")
(command "-COLOR" "7")
(command "-TEXT" "S" "Standard" "J" "C" (list 14855 -5) 8 0 "SW-TEL (Meraki MS225)")
(command "-LAYER" "S" "Switches" "")
(command "-COLOR" "6")
(command "_.PLINE" (list 14850 40) (list 14970 40) (list 14970 80) (list 14850 80) "C")
(command "-LAYER" "S" "Textos" "")
(command "-COLOR" "7")
(command "-TEXT" "S" "Standard" "J" "C" (list 14855 55) 8 0 "SW-WIFI (Meraki MS225)")
(princ "DONE.")
(princ "\n   - Dibujando dispositivos por nivel...")
(command "-LAYER" "S" "Camaras" "")
(command "-COLOR" "1")
(command "_.PLINE" (list 14840.0 150) (list 14860.0 150) (list 14860.0 165) (list 14840.0 165) "C")
(command "_.CIRCLE" (list 14850 157.5) 3)
(command "-LAYER" "S" "Textos" "")
(command "-COLOR" "7")
(command "-TEXT" "S" "Standard" "J" "C" (list 14850 130) 10 0 "1xCCTV")
(command "-LAYER" "S" "Datos" "")
(command "-COLOR" "1")
(command "_.PLINE" (list 14940.0 150) (list 14960.0 150) (list 14950 170) "C")
(command "-HATCH" "S" "L" "" "")
(command "-LAYER" "S" "Textos" "")
(command "-COLOR" "7")
(command "-TEXT" "S" "Standard" "J" "C" (list 14950 130) 10 0 "2xDATO")
(command "-LAYER" "S" "APs" "")
(command "-COLOR" "3")
(command "_.PLINE" (list 14840.0 350) (list 14860.0 350) (list 14850 375) (list 14840.0 350) "")
(command "_.CIRCLE" (list 14850 375) 10)
(command "_.CIRCLE" (list 14850 375) 21.25)
(command "_.CIRCLE" (list 14850 375) 30)
(command "-LAYER" "S" "Textos" "")
(command "-COLOR" "7")
(command "-TEXT" "S" "Standard" "J" "C" (list 14850 330) 10 0 "9xAP")
(command "-LAYER" "S" "Telefonos" "")
(command "-COLOR" "4")
(command "_.PLINE" (list 14940.0 350) (list 14960.0 350) (list 14960.0 380) (list 14940.0 380) "C")
(command "_.CIRCLE" (list 14950 387) 5)
(command "-LAYER" "S" "Textos" "")
(command "-COLOR" "7")
(command "-TEXT" "S" "Standard" "J" "C" (list 14950 330) 10 0 "10xTEL")
(command "-LAYER" "S" "TVs" "")
(command "-COLOR" "5")
(command "_.PLINE" (list 15030.0 350) (list 15070.0 350) (list 15070.0 375) (list 15030.0 375) "C")
(command "_.PLINE" (list 15040.0 350) (list 15060.0 350) (list 15050 340) (list 15040.0 350) "")
(command "-LAYER" "S" "Textos" "")
(command "-COLOR" "7")
(command "-TEXT" "S" "Standard" "J" "C" (list 15050 330) 10 0 "6xTV")
(command "-LAYER" "S" "Camaras" "")
(command "-COLOR" "1")
(command "_.PLINE" (list 15140.0 350) (list 15160.0 350) (list 15160.0 365) (list 15140.0 365) "C")
(command "_.CIRCLE" (list 15150 357.5) 3)
(command "-LAYER" "S" "Textos" "")
(command "-COLOR" "7")
(command "-TEXT" "S" "Standard" "J" "C" (list 15150 330) 10 0 "3xCCTV")
(command "-LAYER" "S" "Datos" "")
(command "-COLOR" "1")
(command "_.PLINE" (list 15240.0 350) (list 15260.0 350) (list 15250 370) "C")
(command "-HATCH" "S" "L" "" "")
(command "-LAYER" "S" "Textos" "")
(command "-COLOR" "7")
(command "-TEXT" "S" "Standard" "J" "C" (list 15250 330) 10 0 "20xDATO")
(command "-LAYER" "S" "APs" "")
(command "-COLOR" "3")
(command "_.PLINE" (list 14840.0 550) (list 14860.0 550) (list 14850 575) (list 14840.0 550) "")
(command "_.CIRCLE" (list 14850 575) 10)
(command "_.CIRCLE" (list 14850 575) 21.25)
(command "_.CIRCLE" (list 14850 575) 30)
(command "-LAYER" "S" "Textos" "")
(command "-COLOR" "7")
(command "-TEXT" "S" "Standard" "J" "C" (list 14850 530) 10 0 "8xAP")
(command "-LAYER" "S" "Telefonos" "")
(command "-COLOR" "4")
(command "_.PLINE" (list 14940.0 550) (list 14960.0 550) (list 14960.0 580) (list 14940.0 580) "C")
(command "_.CIRCLE" (list 14950 587) 5)
(command "-LAYER" "S" "Textos" "")
(command "-COLOR" "7")
(command "-TEXT" "S" "Standard" "J" "C" (list 14950 530) 10 0 "9xTEL")
(command "-LAYER" "S" "TVs" "")
(command "-COLOR" "5")
(command "_.PLINE" (list 15030.0 550) (list 15070.0 550) (list 15070.0 575) (list 15030.0 575) "C")
(command "_.PLINE" (list 15040.0 550) (list 15060.0 550) (list 15050 540) (list 15040.0 550) "")
(command "-LAYER" "S" "Textos" "")
(command "-COLOR" "7")
(command "-TEXT" "S" "Standard" "J" "C" (list 15050 530) 10 0 "5xTV")
(command "-LAYER" "S" "Camaras" "")
(command "-COLOR" "1")
(command "_.PLINE" (list 15140.0 550) (list 15160.0 550) (list 15160.0 565) (list 15140.0 565) "C")
(command "_.CIRCLE" (list 15150 557.5) 3)
(command "-LAYER" "S" "Textos" "")
(command "-COLOR" "7")
(command "-TEXT" "S" "Standard" "J" "C" (list 15150 530) 10 0 "3xCCTV")
(command "-LAYER" "S" "Datos" "")
(command "-COLOR" "1")
(command "_.PLINE" (list 15240.0 550) (list 15260.0 550) (list 15250 570) "C")
(command "-HATCH" "S" "L" "" "")
(command "-LAYER" "S" "Textos" "")
(command "-COLOR" "7")
(command "-TEXT" "S" "Standard" "J" "C" (list 15250 530) 10 0 "18xDATO")
(command "-LAYER" "S" "APs" "")
(command "-COLOR" "3")
(command "_.PLINE" (list 14840.0 750) (list 14860.0 750) (list 14850 775) (list 14840.0 750) "")
(command "_.CIRCLE" (list 14850 775) 10)
(command "_.CIRCLE" (list 14850 775) 21.25)
(command "_.CIRCLE" (list 14850 775) 30)
(command "-LAYER" "S" "Textos" "")
(command "-COLOR" "7")
(command "-TEXT" "S" "Standard" "J" "C" (list 14850 730) 10 0 "8xAP")
(command "-LAYER" "S" "Telefonos" "")
(command "-COLOR" "4")
(command "_.PLINE" (list 14940.0 750) (list 14960.0 750) (list 14960.0 780) (list 14940.0 780) "C")
(command "_.CIRCLE" (list 14950 787) 5)
(command "-LAYER" "S" "Textos" "")
(command "-COLOR" "7")
(command "-TEXT" "S" "Standard" "J" "C" (list 14950 730) 10 0 "9xTEL")
(command "-LAYER" "S" "TVs" "")
(command "-COLOR" "5")
(command "_.PLINE" (list 15030.0 750) (list 15070.0 750) (list 15070.0 775) (list 15030.0 775) "C")
(command "_.PLINE" (list 15040.0 750) (list 15060.0 750) (list 15050 740) (list 15040.0 750) "")
(command "-LAYER" "S" "Textos" "")
(command "-COLOR" "7")
(command "-TEXT" "S" "Standard" "J" "C" (list 15050 730) 10 0 "5xTV")
(command "-LAYER" "S" "Camaras" "")
(command "-COLOR" "1")
(command "_.PLINE" (list 15140.0 750) (list 15160.0 750) (list 15160.0 765) (list 15140.0 765) "C")
(command "_.CIRCLE" (list 15150 757.5) 3)
(command "-LAYER" "S" "Textos" "")
(command "-COLOR" "7")
(command "-TEXT" "S" "Standard" "J" "C" (list 15150 730) 10 0 "3xCCTV")
(command "-LAYER" "S" "Datos" "")
(command "-COLOR" "1")
(command "_.PLINE" (list 15240.0 750) (list 15260.0 750) (list 15250 770) "C")
(command "-HATCH" "S" "L" "" "")
(command "-LAYER" "S" "Textos" "")
(command "-COLOR" "7")
(command "-TEXT" "S" "Standard" "J" "C" (list 15250 730) 10 0 "18xDATO")
(command "-LAYER" "S" "APs" "")
(command "-COLOR" "3")
(command "_.PLINE" (list 14840.0 950) (list 14860.0 950) (list 14850 975) (list 14840.0 950) "")
(command "_.CIRCLE" (list 14850 975) 10)
(command "_.CIRCLE" (list 14850 975) 21.25)
(command "_.CIRCLE" (list 14850 975) 30)
(command "-LAYER" "S" "Textos" "")
(command "-COLOR" "7")
(command "-TEXT" "S" "Standard" "J" "C" (list 14850 930) 10 0 "8xAP")
(command "-LAYER" "S" "Telefonos" "")
(command "-COLOR" "4")
(command "_.PLINE" (list 14940.0 950) (list 14960.0 950) (list 14960.0 980) (list 14940.0 980) "C")
(command "_.CIRCLE" (list 14950 987) 5)
(command "-LAYER" "S" "Textos" "")
(command "-COLOR" "7")
(command "-TEXT" "S" "Standard" "J" "C" (list 14950 930) 10 0 "9xTEL")
(command "-LAYER" "S" "TVs" "")
(command "-COLOR" "5")
(command "_.PLINE" (list 15030.0 950) (list 15070.0 950) (list 15070.0 975) (list 15030.0 975) "C")
(command "_.PLINE" (list 15040.0 950) (list 15060.0 950) (list 15050 940) (list 15040.0 950) "")
(command "-LAYER" "S" "Textos" "")
(command "-COLOR" "7")
(command "-TEXT" "S" "Standard" "J" "C" (list 15050 930) 10 0 "5xTV")
(command "-LAYER" "S" "Camaras" "")
(command "-COLOR" "1")
(command "_.PLINE" (list 15140.0 950) (list 15160.0 950) (list 15160.0 965) (list 15140.0 965) "C")
(command "_.CIRCLE" (list 15150 957.5) 3)
(command "-LAYER" "S" "Textos" "")
(command "-COLOR" "7")
(command "-TEXT" "S" "Standard" "J" "C" (list 15150 930) 10 0 "3xCCTV")
(command "-LAYER" "S" "Datos" "")
(command "-COLOR" "1")
(command "_.PLINE" (list 15240.0 950) (list 15260.0 950) (list 15250 970) "C")
(command "-HATCH" "S" "L" "" "")
(command "-LAYER" "S" "Textos" "")
(command "-COLOR" "7")
(command "-TEXT" "S" "Standard" "J" "C" (list 15250 930) 10 0 "18xDATO")
(command "-LAYER" "S" "APs" "")
(command "-COLOR" "3")
(command "_.PLINE" (list 14840.0 1150) (list 14860.0 1150) (list 14850 1175) (list 14840.0 1150) "")
(command "_.CIRCLE" (list 14850 1175) 10)
(command "_.CIRCLE" (list 14850 1175) 21.25)
(command "_.CIRCLE" (list 14850 1175) 30)
(command "-LAYER" "S" "Textos" "")
(command "-COLOR" "7")
(command "-TEXT" "S" "Standard" "J" "C" (list 14850 1130) 10 0 "8xAP")
(command "-LAYER" "S" "Telefonos" "")
(command "-COLOR" "4")
(command "_.PLINE" (list 14940.0 1150) (list 14960.0 1150) (list 14960.0 1180) (list 14940.0 1180) "C")
(command "_.CIRCLE" (list 14950 1187) 5)
(command "-LAYER" "S" "Textos" "")
(command "-COLOR" "7")
(command "-TEXT" "S" "Standard" "J" "C" (list 14950 1130) 10 0 "9xTEL")
(command "-LAYER" "S" "TVs" "")
(command "-COLOR" "5")
(command "_.PLINE" (list 15030.0 1150) (list 15070.0 1150) (list 15070.0 1175) (list 15030.0 1175) "C")
(command "_.PLINE" (list 15040.0 1150) (list 15060.0 1150) (list 15050 1140) (list 15040.0 1150) "")
(command "-LAYER" "S" "Textos" "")
(command "-COLOR" "7")
(command "-TEXT" "S" "Standard" "J" "C" (list 15050 1130) 10 0 "5xTV")
(command "-LAYER" "S" "Camaras" "")
(command "-COLOR" "1")
(command "_.PLINE" (list 15140.0 1150) (list 15160.0 1150) (list 15160.0 1165) (list 15140.0 1165) "C")
(command "_.CIRCLE" (list 15150 1157.5) 3)
(command "-LAYER" "S" "Textos" "")
(command "-COLOR" "7")
(command "-TEXT" "S" "Standard" "J" "C" (list 15150 1130) 10 0 "3xCCTV")
(command "-LAYER" "S" "Datos" "")
(command "-COLOR" "1")
(command "_.PLINE" (list 15240.0 1150) (list 15260.0 1150) (list 15250 1170) "C")
(command "-HATCH" "S" "L" "" "")
(command "-LAYER" "S" "Textos" "")
(command "-COLOR" "7")
(command "-TEXT" "S" "Standard" "J" "C" (list 15250 1130) 10 0 "18xDATO")
(command "-LAYER" "S" "APs" "")
(command "-COLOR" "3")
(command "_.PLINE" (list 14840.0 1350) (list 14860.0 1350) (list 14850 1375) (list 14840.0 1350) "")
(command "_.CIRCLE" (list 14850 1375) 10)
(command "_.CIRCLE" (list 14850 1375) 21.25)
(command "_.CIRCLE" (list 14850 1375) 30)
(command "-LAYER" "S" "Textos" "")
(command "-COLOR" "7")
(command "-TEXT" "S" "Standard" "J" "C" (list 14850 1330) 10 0 "8xAP")
(command "-LAYER" "S" "Telefonos" "")
(command "-COLOR" "4")
(command "_.PLINE" (list 14940.0 1350) (list 14960.0 1350) (list 14960.0 1380) (list 14940.0 1380) "C")
(command "_.CIRCLE" (list 14950 1387) 5)
(command "-LAYER" "S" "Textos" "")
(command "-COLOR" "7")
(command "-TEXT" "S" "Standard" "J" "C" (list 14950 1330) 10 0 "9xTEL")
(command "-LAYER" "S" "TVs" "")
(command "-COLOR" "5")
(command "_.PLINE" (list 15030.0 1350) (list 15070.0 1350) (list 15070.0 1375) (list 15030.0 1375) "C")
(command "_.PLINE" (list 15040.0 1350) (list 15060.0 1350) (list 15050 1340) (list 15040.0 1350) "")
(command "-LAYER" "S" "Textos" "")
(command "-COLOR" "7")
(command "-TEXT" "S" "Standard" "J" "C" (list 15050 1330) 10 0 "5xTV")
(command "-LAYER" "S" "Camaras" "")
(command "-COLOR" "1")
(command "_.PLINE" (list 15140.0 1350) (list 15160.0 1350) (list 15160.0 1365) (list 15140.0 1365) "C")
(command "_.CIRCLE" (list 15150 1357.5) 3)
(command "-LAYER" "S" "Textos" "")
(command "-COLOR" "7")
(command "-TEXT" "S" "Standard" "J" "C" (list 15150 1330) 10 0 "3xCCTV")
(command "-LAYER" "S" "Datos" "")
(command "-COLOR" "1")
(command "_.PLINE" (list 15240.0 1350) (list 15260.0 1350) (list 15250 1370) "C")
(command "-HATCH" "S" "L" "" "")
(command "-LAYER" "S" "Textos" "")
(command "-COLOR" "7")
(command "-TEXT" "S" "Standard" "J" "C" (list 15250 1330) 10 0 "18xDATO")
(command "-LAYER" "S" "APs" "")
(command "-COLOR" "3")
(command "_.PLINE" (list 14840.0 1550) (list 14860.0 1550) (list 14850 1575) (list 14840.0 1550) "")
(command "_.CIRCLE" (list 14850 1575) 10)
(command "_.CIRCLE" (list 14850 1575) 21.25)
(command "_.CIRCLE" (list 14850 1575) 30)
(command "-LAYER" "S" "Textos" "")
(command "-COLOR" "7")
(command "-TEXT" "S" "Standard" "J" "C" (list 14850 1530) 10 0 "4xAP")
(command "-LAYER" "S" "Telefonos" "")
(command "-COLOR" "4")
(command "_.PLINE" (list 14940.0 1550) (list 14960.0 1550) (list 14960.0 1580) (list 14940.0 1580) "C")
(command "_.CIRCLE" (list 14950 1587) 5)
(command "-LAYER" "S" "Textos" "")
(command "-COLOR" "7")
(command "-TEXT" "S" "Standard" "J" "C" (list 14950 1530) 10 0 "4xTEL")
(command "-LAYER" "S" "TVs" "")
(command "-COLOR" "5")
(command "_.PLINE" (list 15030.0 1550) (list 15070.0 1550) (list 15070.0 1575) (list 15030.0 1575) "C")
(command "_.PLINE" (list 15040.0 1550) (list 15060.0 1550) (list 15050 1540) (list 15040.0 1550) "")
(command "-LAYER" "S" "Textos" "")
(command "-COLOR" "7")
(command "-TEXT" "S" "Standard" "J" "C" (list 15050 1530) 10 0 "3xTV")
(command "-LAYER" "S" "Camaras" "")
(command "-COLOR" "1")
(command "_.PLINE" (list 15140.0 1550) (list 15160.0 1550) (list 15160.0 1565) (list 15140.0 1565) "C")
(command "_.CIRCLE" (list 15150 1557.5) 3)
(command "-LAYER" "S" "Textos" "")
(command "-COLOR" "7")
(command "-TEXT" "S" "Standard" "J" "C" (list 15150 1530) 10 0 "2xCCTV")
(command "-LAYER" "S" "Datos" "")
(command "-COLOR" "1")
(command "_.PLINE" (list 15240.0 1550) (list 15260.0 1550) (list 15250 1570) "C")
(command "-HATCH" "S" "L" "" "")
(command "-LAYER" "S" "Textos" "")
(command "-COLOR" "7")
(command "-TEXT" "S" "Standard" "J" "C" (list 15250 1530) 10 0 "10xDATO")
(princ "DONE.")

; === DIBUJAR TORRE: IDF15 BAR PISCINA ===
(princ "\n>> Dibujando Torre: IDF15 BAR PISCINA...")
(command "-LAYER" "S" "Textos" "")
(command "-COLOR" "7")
(command "-TEXT" "S" "Standard" "J" "C" (list 15850 150) 25 0 "IDF15 BAR PISCINA")
(princ "\n   - Dibujando switches...")
(command "-LAYER" "S" "Switches" "")
(command "-COLOR" "6")
(command "_.PLINE" (list 15900 -200) (list 16020 -200) (list 16020 -160) (list 15900 -160) "C")
(command "-LAYER" "S" "Textos" "")
(command "-COLOR" "7")
(command "-TEXT" "S" "Standard" "J" "C" (list 15905 -185) 8 0 "SW-CCTV (DS-3E3728F)")
(command "-LAYER" "S" "Switches" "")
(command "-COLOR" "6")
(command "_.PLINE" (list 15900 -140) (list 16020 -140) (list 16020 -100) (list 15900 -100) "C")
(command "-LAYER" "S" "Textos" "")
(command "-COLOR" "7")
(command "-TEXT" "S" "Standard" "J" "C" (list 15905 -125) 8 0 "SW-DATA (Meraki MS225)")
(command "-LAYER" "S" "Switches" "")
(command "-COLOR" "6")
(command "_.PLINE" (list 15900 -80) (list 16020 -80) (list 16020 -40) (list 15900 -40) "C")
(command "-LAYER" "S" "Textos" "")
(command "-COLOR" "7")
(command "-TEXT" "S" "Standard" "J" "C" (list 15905 -65) 8 0 "SW-IPTV (RG-NBS6002)")
(command "-LAYER" "S" "Switches" "")
(command "-COLOR" "6")
(command "_.PLINE" (list 15900 -20) (list 16020 -20) (list 16020 20) (list 15900 20) "C")
(command "-LAYER" "S" "Textos" "")
(command "-COLOR" "7")
(command "-TEXT" "S" "Standard" "J" "C" (list 15905 -5) 8 0 "SW-TEL (Meraki MS225)")
(command "-LAYER" "S" "Switches" "")
(command "-COLOR" "6")
(command "_.PLINE" (list 15900 40) (list 16020 40) (list 16020 80) (list 15900 80) "C")
(command "-LAYER" "S" "Textos" "")
(command "-COLOR" "7")
(command "-TEXT" "S" "Standard" "J" "C" (list 15905 55) 8 0 "SW-WIFI (Meraki MS225)")
(princ "DONE.")
(princ "\n   - Dibujando dispositivos por nivel...")
(command "-LAYER" "S" "Telefonos" "")
(command "-COLOR" "4")
(command "_.PLINE" (list 15890.0 350) (list 15910.0 350) (list 15910.0 380) (list 15890.0 380) "C")
(command "_.CIRCLE" (list 15900 387) 5)
(command "-LAYER" "S" "Textos" "")
(command "-COLOR" "7")
(command "-TEXT" "S" "Standard" "J" "C" (list 15900 330) 10 0 "2xTEL")
(command "-LAYER" "S" "TVs" "")
(command "-COLOR" "5")
(command "_.PLINE" (list 15980.0 350) (list 16020.0 350) (list 16020.0 375) (list 15980.0 375) "C")
(command "_.PLINE" (list 15990.0 350) (list 16010.0 350) (list 16000 340) (list 15990.0 350) "")
(command "-LAYER" "S" "Textos" "")
(command "-COLOR" "7")
(command "-TEXT" "S" "Standard" "J" "C" (list 16000 330) 10 0 "1xTV")
(command "-LAYER" "S" "Camaras" "")
(command "-COLOR" "1")
(command "_.PLINE" (list 16090.0 350) (list 16110.0 350) (list 16110.0 365) (list 16090.0 365) "C")
(command "_.CIRCLE" (list 16100 357.5) 3)
(command "-LAYER" "S" "Textos" "")
(command "-COLOR" "7")
(command "-TEXT" "S" "Standard" "J" "C" (list 16100 330) 10 0 "1xCCTV")
(command "-LAYER" "S" "Datos" "")
(command "-COLOR" "1")
(command "_.PLINE" (list 16190.0 350) (list 16210.0 350) (list 16200 370) "C")
(command "-HATCH" "S" "L" "" "")
(command "-LAYER" "S" "Textos" "")
(command "-COLOR" "7")
(command "-TEXT" "S" "Standard" "J" "C" (list 16200 330) 10 0 "4xDATO")
(princ "DONE.")

; === DIBUJAR CABLES ===
(princ "\nDibujando cables UTP...")
(command "-LAYER" "S" "Cables_UTP" "")
(command "-COLOR" "5")
(command "_.PLINE" (list 150 150) (list 150 100) (list 210.0 100) (list 210.0 80) "")
(command "-LAYER" "S" "Cables_UTP" "")
(command "-COLOR" "5")
(command "-TEXT" "S" "Standard" "J" "C" (list 165 125.0) 10 0 "1xUTP")
(command "-LAYER" "S" "Cables_UTP" "")
(command "-COLOR" "5")
(command "_.PLINE" (list 1200 150) (list 1200 100) (list 1260.0 100) (list 1260.0 80) "")
(command "-LAYER" "S" "Cables_UTP" "")
(command "-COLOR" "5")
(command "-TEXT" "S" "Standard" "J" "C" (list 1215 125.0) 10 0 "1xUTP")
(command "-LAYER" "S" "Cables_UTP" "")
(command "-COLOR" "5")
(command "_.PLINE" (list 1200 350) (list 1200 40) (list 1260.0 40) (list 1260.0 20) "")
(command "-LAYER" "S" "Cables_UTP" "")
(command "-COLOR" "5")
(command "-TEXT" "S" "Standard" "J" "C" (list 1215 195.0) 10 0 "1xUTP")
(command "-LAYER" "S" "Cables_UTP" "")
(command "-COLOR" "5")
(command "_.PLINE" (list 1200 550) (list 1200 -20) (list 1260.0 -20) (list 1260.0 -40) "")
(command "-LAYER" "S" "Cables_UTP" "")
(command "-COLOR" "5")
(command "-TEXT" "S" "Standard" "J" "C" (list 1215 265.0) 10 0 "1xUTP")
(command "-LAYER" "S" "Cables_UTP" "")
(command "-COLOR" "5")
(command "_.PLINE" (list 1200 750) (list 1200 -140) (list 1260.0 -140) (list 1260.0 -160) "")
(command "-LAYER" "S" "Cables_UTP" "")
(command "-COLOR" "5")
(command "-TEXT" "S" "Standard" "J" "C" (list 1215 305.0) 10 0 "1xUTP")
(command "-LAYER" "S" "Cables_UTP" "")
(command "-COLOR" "5")
(command "_.PLINE" (list 1200 950) (list 1200 -80) (list 1260.0 -80) (list 1260.0 -100) "")
(command "-LAYER" "S" "Cables_UTP" "")
(command "-COLOR" "5")
(command "-TEXT" "S" "Standard" "J" "C" (list 1215 435.0) 10 0 "1xUTP")
(command "-LAYER" "S" "Cables_UTP" "")
(command "-COLOR" "5")
(command "_.PLINE" (list 1200 1150) (list 1200 100) (list 1260.0 100) (list 1260.0 80) "")
(command "-LAYER" "S" "Cables_UTP" "")
(command "-COLOR" "5")
(command "-TEXT" "S" "Standard" "J" "C" (list 1215 625.0) 10 0 "4xUTP")
(command "-LAYER" "S" "Cables_UTP" "")
(command "-COLOR" "5")
(command "_.PLINE" (list 1300 1150) (list 1300 40) (list 1260.0 40) (list 1260.0 20) "")
(command "-LAYER" "S" "Cables_UTP" "")
(command "-COLOR" "5")
(command "-TEXT" "S" "Standard" "J" "C" (list 1315 595.0) 10 0 "4xUTP")
(command "-LAYER" "S" "Cables_UTP" "")
(command "-COLOR" "5")
(command "_.PLINE" (list 1400 1150) (list 1400 -20) (list 1260.0 -20) (list 1260.0 -40) "")
(command "-LAYER" "S" "Cables_UTP" "")
(command "-COLOR" "5")
(command "-TEXT" "S" "Standard" "J" "C" (list 1415 565.0) 10 0 "2xUTP")
(command "-LAYER" "S" "Cables_UTP" "")
(command "-COLOR" "5")
(command "_.PLINE" (list 1500 1150) (list 1500 -140) (list 1260.0 -140) (list 1260.0 -160) "")
(command "-LAYER" "S" "Cables_UTP" "")
(command "-COLOR" "5")
(command "-TEXT" "S" "Standard" "J" "C" (list 1515 505.0) 10 0 "1xUTP")
(command "-LAYER" "S" "Cables_UTP" "")
(command "-COLOR" "5")
(command "_.PLINE" (list 1600 1150) (list 1600 -80) (list 1260.0 -80) (list 1260.0 -100) "")
(command "-LAYER" "S" "Cables_UTP" "")
(command "-COLOR" "5")
(command "-TEXT" "S" "Standard" "J" "C" (list 1615 535.0) 10 0 "10xUTP")
(command "-LAYER" "S" "Cables_UTP" "")
(command "-COLOR" "5")
(command "_.PLINE" (list 1200 1350) (list 1200 100) (list 1260.0 100) (list 1260.0 80) "")
(command "-LAYER" "S" "Cables_UTP" "")
(command "-COLOR" "5")
(command "-TEXT" "S" "Standard" "J" "C" (list 1215 725.0) 10 0 "4xUTP")
(command "-LAYER" "S" "Cables_UTP" "")
(command "-COLOR" "5")
(command "_.PLINE" (list 1300 1350) (list 1300 40) (list 1260.0 40) (list 1260.0 20) "")
(command "-LAYER" "S" "Cables_UTP" "")
(command "-COLOR" "5")
(command "-TEXT" "S" "Standard" "J" "C" (list 1315 695.0) 10 0 "4xUTP")
(command "-LAYER" "S" "Cables_UTP" "")
(command "-COLOR" "5")
(command "_.PLINE" (list 1400 1350) (list 1400 -20) (list 1260.0 -20) (list 1260.0 -40) "")
(command "-LAYER" "S" "Cables_UTP" "")
(command "-COLOR" "5")
(command "-TEXT" "S" "Standard" "J" "C" (list 1415 665.0) 10 0 "2xUTP")
(command "-LAYER" "S" "Cables_UTP" "")
(command "-COLOR" "5")
(command "_.PLINE" (list 1500 1350) (list 1500 -140) (list 1260.0 -140) (list 1260.0 -160) "")
(command "-LAYER" "S" "Cables_UTP" "")
(command "-COLOR" "5")
(command "-TEXT" "S" "Standard" "J" "C" (list 1515 605.0) 10 0 "1xUTP")
(command "-LAYER" "S" "Cables_UTP" "")
(command "-COLOR" "5")
(command "_.PLINE" (list 1600 1350) (list 1600 -80) (list 1260.0 -80) (list 1260.0 -100) "")
(command "-LAYER" "S" "Cables_UTP" "")
(command "-COLOR" "5")
(command "-TEXT" "S" "Standard" "J" "C" (list 1615 635.0) 10 0 "10xUTP")
(command "-LAYER" "S" "Cables_UTP" "")
(command "-COLOR" "5")
(command "_.PLINE" (list 1200 1550) (list 1200 100) (list 1260.0 100) (list 1260.0 80) "")
(command "-LAYER" "S" "Cables_UTP" "")
(command "-COLOR" "5")
(command "-TEXT" "S" "Standard" "J" "C" (list 1215 825.0) 10 0 "2xUTP")
(command "-LAYER" "S" "Cables_UTP" "")
(command "-COLOR" "5")
(command "_.PLINE" (list 1300 1550) (list 1300 40) (list 1260.0 40) (list 1260.0 20) "")
(command "-LAYER" "S" "Cables_UTP" "")
(command "-COLOR" "5")
(command "-TEXT" "S" "Standard" "J" "C" (list 1315 795.0) 10 0 "2xUTP")
(command "-LAYER" "S" "Cables_UTP" "")
(command "-COLOR" "5")
(command "_.PLINE" (list 1400 1550) (list 1400 -20) (list 1260.0 -20) (list 1260.0 -40) "")
(command "-LAYER" "S" "Cables_UTP" "")
(command "-COLOR" "5")
(command "-TEXT" "S" "Standard" "J" "C" (list 1415 765.0) 10 0 "1xUTP")
(command "-LAYER" "S" "Cables_UTP" "")
(command "-COLOR" "5")
(command "_.PLINE" (list 1500 1550) (list 1500 -140) (list 1260.0 -140) (list 1260.0 -160) "")
(command "-LAYER" "S" "Cables_UTP" "")
(command "-COLOR" "5")
(command "-TEXT" "S" "Standard" "J" "C" (list 1515 705.0) 10 0 "1xUTP")
(command "-LAYER" "S" "Cables_UTP" "")
(command "-COLOR" "5")
(command "_.PLINE" (list 1600 1550) (list 1600 -80) (list 1260.0 -80) (list 1260.0 -100) "")
(command "-LAYER" "S" "Cables_UTP" "")
(command "-COLOR" "5")
(command "-TEXT" "S" "Standard" "J" "C" (list 1615 735.0) 10 0 "6xUTP")
(command "-LAYER" "S" "Cables_UTP" "")
(command "-COLOR" "5")
(command "_.PLINE" (list 2250 150) (list 2250 40) (list 2310.0 40) (list 2310.0 20) "")
(command "-LAYER" "S" "Cables_UTP" "")
(command "-COLOR" "5")
(command "-TEXT" "S" "Standard" "J" "C" (list 2265 95.0) 10 0 "2xUTP")
(command "-LAYER" "S" "Cables_UTP" "")
(command "-COLOR" "5")
(command "_.PLINE" (list 2350 150) (list 2350 -20) (list 2310.0 -20) (list 2310.0 -40) "")
(command "-LAYER" "S" "Cables_UTP" "")
(command "-COLOR" "5")
(command "-TEXT" "S" "Standard" "J" "C" (list 2365 65.0) 10 0 "1xUTP")
(command "-LAYER" "S" "Cables_UTP" "")
(command "-COLOR" "5")
(command "_.PLINE" (list 2450 150) (list 2450 -140) (list 2310.0 -140) (list 2310.0 -160) "")
(command "-LAYER" "S" "Cables_UTP" "")
(command "-COLOR" "5")
(command "-TEXT" "S" "Standard" "J" "C" (list 2465 5.0) 10 0 "1xUTP")
(command "-LAYER" "S" "Cables_UTP" "")
(command "-COLOR" "5")
(command "_.PLINE" (list 2550 150) (list 2550 -80) (list 2310.0 -80) (list 2310.0 -100) "")
(command "-LAYER" "S" "Cables_UTP" "")
(command "-COLOR" "5")
(command "-TEXT" "S" "Standard" "J" "C" (list 2565 35.0) 10 0 "4xUTP")
(command "-LAYER" "S" "Cables_UTP" "")
(command "-COLOR" "5")
(command "_.PLINE" (list 2250 350) (list 2250 100) (list 2310.0 100) (list 2310.0 80) "")
(command "-LAYER" "S" "Cables_UTP" "")
(command "-COLOR" "5")
(command "-TEXT" "S" "Standard" "J" "C" (list 2265 225.0) 10 0 "5xUTP")
(command "-LAYER" "S" "Cables_UTP" "")
(command "-COLOR" "5")
(command "_.PLINE" (list 2350 350) (list 2350 40) (list 2310.0 40) (list 2310.0 20) "")
(command "-LAYER" "S" "Cables_UTP" "")
(command "-COLOR" "5")
(command "-TEXT" "S" "Standard" "J" "C" (list 2365 195.0) 10 0 "6xUTP")
(command "-LAYER" "S" "Cables_UTP" "")
(command "-COLOR" "5")
(command "_.PLINE" (list 2450 350) (list 2450 -20) (list 2310.0 -20) (list 2310.0 -40) "")
(command "-LAYER" "S" "Cables_UTP" "")
(command "-COLOR" "5")
(command "-TEXT" "S" "Standard" "J" "C" (list 2465 165.0) 10 0 "4xUTP")
(command "-LAYER" "S" "Cables_UTP" "")
(command "-COLOR" "5")
(command "_.PLINE" (list 2550 350) (list 2550 -140) (list 2310.0 -140) (list 2310.0 -160) "")
(command "-LAYER" "S" "Cables_UTP" "")
(command "-COLOR" "5")
(command "-TEXT" "S" "Standard" "J" "C" (list 2565 105.0) 10 0 "2xUTP")
(command "-LAYER" "S" "Cables_UTP" "")
(command "-COLOR" "5")
(command "_.PLINE" (list 2650 350) (list 2650 -80) (list 2310.0 -80) (list 2310.0 -100) "")
(command "-LAYER" "S" "Cables_UTP" "")
(command "-COLOR" "5")
(command "-TEXT" "S" "Standard" "J" "C" (list 2665 135.0) 10 0 "14xUTP")
(command "-LAYER" "S" "Cables_UTP" "")
(command "-COLOR" "5")
(command "_.PLINE" (list 2250 550) (list 2250 100) (list 2310.0 100) (list 2310.0 80) "")
(command "-LAYER" "S" "Cables_UTP" "")
(command "-COLOR" "5")
(command "-TEXT" "S" "Standard" "J" "C" (list 2265 325.0) 10 0 "4xUTP")
(command "-LAYER" "S" "Cables_UTP" "")
(command "-COLOR" "5")
(command "_.PLINE" (list 2350 550) (list 2350 40) (list 2310.0 40) (list 2310.0 20) "")
(command "-LAYER" "S" "Cables_UTP" "")
(command "-COLOR" "5")
(command "-TEXT" "S" "Standard" "J" "C" (list 2365 295.0) 10 0 "4xUTP")
(command "-LAYER" "S" "Cables_UTP" "")
(command "-COLOR" "5")
(command "_.PLINE" (list 2450 550) (list 2450 -20) (list 2310.0 -20) (list 2310.0 -40) "")
(command "-LAYER" "S" "Cables_UTP" "")
(command "-COLOR" "5")
(command "-TEXT" "S" "Standard" "J" "C" (list 2465 265.0) 10 0 "2xUTP")
(command "-LAYER" "S" "Cables_UTP" "")
(command "-COLOR" "5")
(command "_.PLINE" (list 2550 550) (list 2550 -140) (list 2310.0 -140) (list 2310.0 -160) "")
(command "-LAYER" "S" "Cables_UTP" "")
(command "-COLOR" "5")
(command "-TEXT" "S" "Standard" "J" "C" (list 2565 205.0) 10 0 "1xUTP")
(command "-LAYER" "S" "Cables_UTP" "")
(command "-COLOR" "5")
(command "_.PLINE" (list 2650 550) (list 2650 -80) (list 2310.0 -80) (list 2310.0 -100) "")
(command "-LAYER" "S" "Cables_UTP" "")
(command "-COLOR" "5")
(command "-TEXT" "S" "Standard" "J" "C" (list 2665 235.0) 10 0 "10xUTP")
(command "-LAYER" "S" "Cables_UTP" "")
(command "-COLOR" "5")
(command "_.PLINE" (list 2250 750) (list 2250 100) (list 2310.0 100) (list 2310.0 80) "")
(command "-LAYER" "S" "Cables_UTP" "")
(command "-COLOR" "5")
(command "-TEXT" "S" "Standard" "J" "C" (list 2265 425.0) 10 0 "4xUTP")
(command "-LAYER" "S" "Cables_UTP" "")
(command "-COLOR" "5")
(command "_.PLINE" (list 2350 750) (list 2350 40) (list 2310.0 40) (list 2310.0 20) "")
(command "-LAYER" "S" "Cables_UTP" "")
(command "-COLOR" "5")
(command "-TEXT" "S" "Standard" "J" "C" (list 2365 395.0) 10 0 "4xUTP")
(command "-LAYER" "S" "Cables_UTP" "")
(command "-COLOR" "5")
(command "_.PLINE" (list 2450 750) (list 2450 -20) (list 2310.0 -20) (list 2310.0 -40) "")
(command "-LAYER" "S" "Cables_UTP" "")
(command "-COLOR" "5")
(command "-TEXT" "S" "Standard" "J" "C" (list 2465 365.0) 10 0 "2xUTP")
(command "-LAYER" "S" "Cables_UTP" "")
(command "-COLOR" "5")
(command "_.PLINE" (list 2550 750) (list 2550 -140) (list 2310.0 -140) (list 2310.0 -160) "")
(command "-LAYER" "S" "Cables_UTP" "")
(command "-COLOR" "5")
(command "-TEXT" "S" "Standard" "J" "C" (list 2565 305.0) 10 0 "1xUTP")
(command "-LAYER" "S" "Cables_UTP" "")
(command "-COLOR" "5")
(command "_.PLINE" (list 2650 750) (list 2650 -80) (list 2310.0 -80) (list 2310.0 -100) "")
(command "-LAYER" "S" "Cables_UTP" "")
(command "-COLOR" "5")
(command "-TEXT" "S" "Standard" "J" "C" (list 2665 335.0) 10 0 "10xUTP")
(command "-LAYER" "S" "Cables_UTP" "")
(command "-COLOR" "5")
(command "_.PLINE" (list 2250 950) (list 2250 100) (list 2310.0 100) (list 2310.0 80) "")
(command "-LAYER" "S" "Cables_UTP" "")
(command "-COLOR" "5")
(command "-TEXT" "S" "Standard" "J" "C" (list 2265 525.0) 10 0 "4xUTP")
(command "-LAYER" "S" "Cables_UTP" "")
(command "-COLOR" "5")
(command "_.PLINE" (list 2350 950) (list 2350 40) (list 2310.0 40) (list 2310.0 20) "")
(command "-LAYER" "S" "Cables_UTP" "")
(command "-COLOR" "5")
(command "-TEXT" "S" "Standard" "J" "C" (list 2365 495.0) 10 0 "4xUTP")
(command "-LAYER" "S" "Cables_UTP" "")
(command "-COLOR" "5")
(command "_.PLINE" (list 2450 950) (list 2450 -20) (list 2310.0 -20) (list 2310.0 -40) "")
(command "-LAYER" "S" "Cables_UTP" "")
(command "-COLOR" "5")
(command "-TEXT" "S" "Standard" "J" "C" (list 2465 465.0) 10 0 "2xUTP")
(command "-LAYER" "S" "Cables_UTP" "")
(command "-COLOR" "5")
(command "_.PLINE" (list 2550 950) (list 2550 -140) (list 2310.0 -140) (list 2310.0 -160) "")
(command "-LAYER" "S" "Cables_UTP" "")
(command "-COLOR" "5")
(command "-TEXT" "S" "Standard" "J" "C" (list 2565 405.0) 10 0 "1xUTP")
(command "-LAYER" "S" "Cables_UTP" "")
(command "-COLOR" "5")
(command "_.PLINE" (list 2650 950) (list 2650 -80) (list 2310.0 -80) (list 2310.0 -100) "")
(command "-LAYER" "S" "Cables_UTP" "")
(command "-COLOR" "5")
(command "-TEXT" "S" "Standard" "J" "C" (list 2665 435.0) 10 0 "10xUTP")
(command "-LAYER" "S" "Cables_UTP" "")
(command "-COLOR" "5")
(command "_.PLINE" (list 2250 1150) (list 2250 100) (list 2310.0 100) (list 2310.0 80) "")
(command "-LAYER" "S" "Cables_UTP" "")
(command "-COLOR" "5")
(command "-TEXT" "S" "Standard" "J" "C" (list 2265 625.0) 10 0 "4xUTP")
(command "-LAYER" "S" "Cables_UTP" "")
(command "-COLOR" "5")
(command "_.PLINE" (list 2350 1150) (list 2350 40) (list 2310.0 40) (list 2310.0 20) "")
(command "-LAYER" "S" "Cables_UTP" "")
(command "-COLOR" "5")
(command "-TEXT" "S" "Standard" "J" "C" (list 2365 595.0) 10 0 "4xUTP")
(command "-LAYER" "S" "Cables_UTP" "")
(command "-COLOR" "5")
(command "_.PLINE" (list 2450 1150) (list 2450 -20) (list 2310.0 -20) (list 2310.0 -40) "")
(command "-LAYER" "S" "Cables_UTP" "")
(command "-COLOR" "5")
(command "-TEXT" "S" "Standard" "J" "C" (list 2465 565.0) 10 0 "2xUTP")
(command "-LAYER" "S" "Cables_UTP" "")
(command "-COLOR" "5")
(command "_.PLINE" (list 2550 1150) (list 2550 -140) (list 2310.0 -140) (list 2310.0 -160) "")
(command "-LAYER" "S" "Cables_UTP" "")
(command "-COLOR" "5")
(command "-TEXT" "S" "Standard" "J" "C" (list 2565 505.0) 10 0 "1xUTP")
(command "-LAYER" "S" "Cables_UTP" "")
(command "-COLOR" "5")
(command "_.PLINE" (list 2650 1150) (list 2650 -80) (list 2310.0 -80) (list 2310.0 -100) "")
(command "-LAYER" "S" "Cables_UTP" "")
(command "-COLOR" "5")
(command "-TEXT" "S" "Standard" "J" "C" (list 2665 535.0) 10 0 "10xUTP")
(command "-LAYER" "S" "Cables_UTP" "")
(command "-COLOR" "5")
(command "_.PLINE" (list 2250 1350) (list 2250 100) (list 2310.0 100) (list 2310.0 80) "")
(command "-LAYER" "S" "Cables_UTP" "")
(command "-COLOR" "5")
(command "-TEXT" "S" "Standard" "J" "C" (list 2265 725.0) 10 0 "4xUTP")
(command "-LAYER" "S" "Cables_UTP" "")
(command "-COLOR" "5")
(command "_.PLINE" (list 2350 1350) (list 2350 40) (list 2310.0 40) (list 2310.0 20) "")
(command "-LAYER" "S" "Cables_UTP" "")
(command "-COLOR" "5")
(command "-TEXT" "S" "Standard" "J" "C" (list 2365 695.0) 10 0 "4xUTP")
(command "-LAYER" "S" "Cables_UTP" "")
(command "-COLOR" "5")
(command "_.PLINE" (list 2450 1350) (list 2450 -20) (list 2310.0 -20) (list 2310.0 -40) "")
(command "-LAYER" "S" "Cables_UTP" "")
(command "-COLOR" "5")
(command "-TEXT" "S" "Standard" "J" "C" (list 2465 665.0) 10 0 "2xUTP")
(command "-LAYER" "S" "Cables_UTP" "")
(command "-COLOR" "5")
(command "_.PLINE" (list 2550 1350) (list 2550 -140) (list 2310.0 -140) (list 2310.0 -160) "")
(command "-LAYER" "S" "Cables_UTP" "")
(command "-COLOR" "5")
(command "-TEXT" "S" "Standard" "J" "C" (list 2565 605.0) 10 0 "1xUTP")
(command "-LAYER" "S" "Cables_UTP" "")
(command "-COLOR" "5")
(command "_.PLINE" (list 2650 1350) (list 2650 -80) (list 2310.0 -80) (list 2310.0 -100) "")
(command "-LAYER" "S" "Cables_UTP" "")
(command "-COLOR" "5")
(command "-TEXT" "S" "Standard" "J" "C" (list 2665 635.0) 10 0 "10xUTP")
(command "-LAYER" "S" "Cables_UTP" "")
(command "-COLOR" "5")
(command "_.PLINE" (list 2250 1550) (list 2250 100) (list 2310.0 100) (list 2310.0 80) "")
(command "-LAYER" "S" "Cables_UTP" "")
(command "-COLOR" "5")
(command "-TEXT" "S" "Standard" "J" "C" (list 2265 825.0) 10 0 "2xUTP")
(command "-LAYER" "S" "Cables_UTP" "")
(command "-COLOR" "5")
(command "_.PLINE" (list 2350 1550) (list 2350 40) (list 2310.0 40) (list 2310.0 20) "")
(command "-LAYER" "S" "Cables_UTP" "")
(command "-COLOR" "5")
(command "-TEXT" "S" "Standard" "J" "C" (list 2365 795.0) 10 0 "2xUTP")
(command "-LAYER" "S" "Cables_UTP" "")
(command "-COLOR" "5")
(command "_.PLINE" (list 2450 1550) (list 2450 -20) (list 2310.0 -20) (list 2310.0 -40) "")
(command "-LAYER" "S" "Cables_UTP" "")
(command "-COLOR" "5")
(command "-TEXT" "S" "Standard" "J" "C" (list 2465 765.0) 10 0 "1xUTP")
(command "-LAYER" "S" "Cables_UTP" "")
(command "-COLOR" "5")
(command "_.PLINE" (list 2550 1550) (list 2550 -140) (list 2310.0 -140) (list 2310.0 -160) "")
(command "-LAYER" "S" "Cables_UTP" "")
(command "-COLOR" "5")
(command "-TEXT" "S" "Standard" "J" "C" (list 2565 705.0) 10 0 "1xUTP")
(command "-LAYER" "S" "Cables_UTP" "")
(command "-COLOR" "5")
(command "_.PLINE" (list 2650 1550) (list 2650 -80) (list 2310.0 -80) (list 2310.0 -100) "")
(command "-LAYER" "S" "Cables_UTP" "")
(command "-COLOR" "5")
(command "-TEXT" "S" "Standard" "J" "C" (list 2665 735.0) 10 0 "6xUTP")
(command "-LAYER" "S" "Cables_UTP" "")
(command "-COLOR" "5")
(command "_.PLINE" (list 3300 150) (list 3300 100) (list 3360.0 100) (list 3360.0 80) "")
(command "-LAYER" "S" "Cables_UTP" "")
(command "-COLOR" "5")
(command "-TEXT" "S" "Standard" "J" "C" (list 3315 125.0) 10 0 "1xUTP")
(command "-LAYER" "S" "Cables_UTP" "")
(command "-COLOR" "5")
(command "_.PLINE" (list 3400 150) (list 3400 40) (list 3360.0 40) (list 3360.0 20) "")
(command "-LAYER" "S" "Cables_UTP" "")
(command "-COLOR" "5")
(command "-TEXT" "S" "Standard" "J" "C" (list 3415 95.0) 10 0 "2xUTP")
(command "-LAYER" "S" "Cables_UTP" "")
(command "-COLOR" "5")
(command "_.PLINE" (list 3500 150) (list 3500 -20) (list 3360.0 -20) (list 3360.0 -40) "")
(command "-LAYER" "S" "Cables_UTP" "")
(command "-COLOR" "5")
(command "-TEXT" "S" "Standard" "J" "C" (list 3515 65.0) 10 0 "1xUTP")
(command "-LAYER" "S" "Cables_UTP" "")
(command "-COLOR" "5")
(command "_.PLINE" (list 3600 150) (list 3600 -140) (list 3360.0 -140) (list 3360.0 -160) "")
(command "-LAYER" "S" "Cables_UTP" "")
(command "-COLOR" "5")
(command "-TEXT" "S" "Standard" "J" "C" (list 3615 5.0) 10 0 "1xUTP")
(command "-LAYER" "S" "Cables_UTP" "")
(command "-COLOR" "5")
(command "_.PLINE" (list 3700 150) (list 3700 -80) (list 3360.0 -80) (list 3360.0 -100) "")
(command "-LAYER" "S" "Cables_UTP" "")
(command "-COLOR" "5")
(command "-TEXT" "S" "Standard" "J" "C" (list 3715 35.0) 10 0 "5xUTP")
(command "-LAYER" "S" "Cables_UTP" "")
(command "-COLOR" "5")
(command "_.PLINE" (list 3300 350) (list 3300 100) (list 3360.0 100) (list 3360.0 80) "")
(command "-LAYER" "S" "Cables_UTP" "")
(command "-COLOR" "5")
(command "-TEXT" "S" "Standard" "J" "C" (list 3315 225.0) 10 0 "4xUTP")
(command "-LAYER" "S" "Cables_UTP" "")
(command "-COLOR" "5")
(command "_.PLINE" (list 3400 350) (list 3400 40) (list 3360.0 40) (list 3360.0 20) "")
(command "-LAYER" "S" "Cables_UTP" "")
(command "-COLOR" "5")
(command "-TEXT" "S" "Standard" "J" "C" (list 3415 195.0) 10 0 "5xUTP")
(command "-LAYER" "S" "Cables_UTP" "")
(command "-COLOR" "5")
(command "_.PLINE" (list 3500 350) (list 3500 -20) (list 3360.0 -20) (list 3360.0 -40) "")
(command "-LAYER" "S" "Cables_UTP" "")
(command "-COLOR" "5")
(command "-TEXT" "S" "Standard" "J" "C" (list 3515 165.0) 10 0 "3xUTP")
(command "-LAYER" "S" "Cables_UTP" "")
(command "-COLOR" "5")
(command "_.PLINE" (list 3600 350) (list 3600 -140) (list 3360.0 -140) (list 3360.0 -160) "")
(command "-LAYER" "S" "Cables_UTP" "")
(command "-COLOR" "5")
(command "-TEXT" "S" "Standard" "J" "C" (list 3615 105.0) 10 0 "2xUTP")
(command "-LAYER" "S" "Cables_UTP" "")
(command "-COLOR" "5")
(command "_.PLINE" (list 3700 350) (list 3700 -80) (list 3360.0 -80) (list 3360.0 -100) "")
(command "-LAYER" "S" "Cables_UTP" "")
(command "-COLOR" "5")
(command "-TEXT" "S" "Standard" "J" "C" (list 3715 135.0) 10 0 "12xUTP")
(command "-LAYER" "S" "Cables_UTP" "")
(command "-COLOR" "5")
(command "_.PLINE" (list 3300 550) (list 3300 100) (list 3360.0 100) (list 3360.0 80) "")
(command "-LAYER" "S" "Cables_UTP" "")
(command "-COLOR" "5")
(command "-TEXT" "S" "Standard" "J" "C" (list 3315 325.0) 10 0 "4xUTP")
(command "-LAYER" "S" "Cables_UTP" "")
(command "-COLOR" "5")
(command "_.PLINE" (list 3400 550) (list 3400 40) (list 3360.0 40) (list 3360.0 20) "")
(command "-LAYER" "S" "Cables_UTP" "")
(command "-COLOR" "5")
(command "-TEXT" "S" "Standard" "J" "C" (list 3415 295.0) 10 0 "4xUTP")
(command "-LAYER" "S" "Cables_UTP" "")
(command "-COLOR" "5")
(command "_.PLINE" (list 3500 550) (list 3500 -20) (list 3360.0 -20) (list 3360.0 -40) "")
(command "-LAYER" "S" "Cables_UTP" "")
(command "-COLOR" "5")
(command "-TEXT" "S" "Standard" "J" "C" (list 3515 265.0) 10 0 "2xUTP")
(command "-LAYER" "S" "Cables_UTP" "")
(command "-COLOR" "5")
(command "_.PLINE" (list 3600 550) (list 3600 -140) (list 3360.0 -140) (list 3360.0 -160) "")
(command "-LAYER" "S" "Cables_UTP" "")
(command "-COLOR" "5")
(command "-TEXT" "S" "Standard" "J" "C" (list 3615 205.0) 10 0 "1xUTP")
(command "-LAYER" "S" "Cables_UTP" "")
(command "-COLOR" "5")
(command "_.PLINE" (list 3700 550) (list 3700 -80) (list 3360.0 -80) (list 3360.0 -100) "")
(command "-LAYER" "S" "Cables_UTP" "")
(command "-COLOR" "5")
(command "-TEXT" "S" "Standard" "J" "C" (list 3715 235.0) 10 0 "10xUTP")
(command "-LAYER" "S" "Cables_UTP" "")
(command "-COLOR" "5")
(command "_.PLINE" (list 3300 750) (list 3300 100) (list 3360.0 100) (list 3360.0 80) "")
(command "-LAYER" "S" "Cables_UTP" "")
(command "-COLOR" "5")
(command "-TEXT" "S" "Standard" "J" "C" (list 3315 425.0) 10 0 "4xUTP")
(command "-LAYER" "S" "Cables_UTP" "")
(command "-COLOR" "5")
(command "_.PLINE" (list 3400 750) (list 3400 40) (list 3360.0 40) (list 3360.0 20) "")
(command "-LAYER" "S" "Cables_UTP" "")
(command "-COLOR" "5")
(command "-TEXT" "S" "Standard" "J" "C" (list 3415 395.0) 10 0 "4xUTP")
(command "-LAYER" "S" "Cables_UTP" "")
(command "-COLOR" "5")
(command "_.PLINE" (list 3500 750) (list 3500 -20) (list 3360.0 -20) (list 3360.0 -40) "")
(command "-LAYER" "S" "Cables_UTP" "")
(command "-COLOR" "5")
(command "-TEXT" "S" "Standard" "J" "C" (list 3515 365.0) 10 0 "2xUTP")
(command "-LAYER" "S" "Cables_UTP" "")
(command "-COLOR" "5")
(command "_.PLINE" (list 3600 750) (list 3600 -140) (list 3360.0 -140) (list 3360.0 -160) "")
(command "-LAYER" "S" "Cables_UTP" "")
(command "-COLOR" "5")
(command "-TEXT" "S" "Standard" "J" "C" (list 3615 305.0) 10 0 "1xUTP")
(command "-LAYER" "S" "Cables_UTP" "")
(command "-COLOR" "5")
(command "_.PLINE" (list 3700 750) (list 3700 -80) (list 3360.0 -80) (list 3360.0 -100) "")
(command "-LAYER" "S" "Cables_UTP" "")
(command "-COLOR" "5")
(command "-TEXT" "S" "Standard" "J" "C" (list 3715 335.0) 10 0 "10xUTP")
(command "-LAYER" "S" "Cables_UTP" "")
(command "-COLOR" "5")
(command "_.PLINE" (list 3300 950) (list 3300 100) (list 3360.0 100) (list 3360.0 80) "")
(command "-LAYER" "S" "Cables_UTP" "")
(command "-COLOR" "5")
(command "-TEXT" "S" "Standard" "J" "C" (list 3315 525.0) 10 0 "4xUTP")
(command "-LAYER" "S" "Cables_UTP" "")
(command "-COLOR" "5")
(command "_.PLINE" (list 3400 950) (list 3400 40) (list 3360.0 40) (list 3360.0 20) "")
(command "-LAYER" "S" "Cables_UTP" "")
(command "-COLOR" "5")
(command "-TEXT" "S" "Standard" "J" "C" (list 3415 495.0) 10 0 "4xUTP")
(command "-LAYER" "S" "Cables_UTP" "")
(command "-COLOR" "5")
(command "_.PLINE" (list 3500 950) (list 3500 -20) (list 3360.0 -20) (list 3360.0 -40) "")
(command "-LAYER" "S" "Cables_UTP" "")
(command "-COLOR" "5")
(command "-TEXT" "S" "Standard" "J" "C" (list 3515 465.0) 10 0 "2xUTP")
(command "-LAYER" "S" "Cables_UTP" "")
(command "-COLOR" "5")
(command "_.PLINE" (list 3600 950) (list 3600 -140) (list 3360.0 -140) (list 3360.0 -160) "")
(command "-LAYER" "S" "Cables_UTP" "")
(command "-COLOR" "5")
(command "-TEXT" "S" "Standard" "J" "C" (list 3615 405.0) 10 0 "1xUTP")
(command "-LAYER" "S" "Cables_UTP" "")
(command "-COLOR" "5")
(command "_.PLINE" (list 3700 950) (list 3700 -80) (list 3360.0 -80) (list 3360.0 -100) "")
(command "-LAYER" "S" "Cables_UTP" "")
(command "-COLOR" "5")
(command "-TEXT" "S" "Standard" "J" "C" (list 3715 435.0) 10 0 "10xUTP")
(command "-LAYER" "S" "Cables_UTP" "")
(command "-COLOR" "5")
(command "_.PLINE" (list 3300 1150) (list 3300 100) (list 3360.0 100) (list 3360.0 80) "")
(command "-LAYER" "S" "Cables_UTP" "")
(command "-COLOR" "5")
(command "-TEXT" "S" "Standard" "J" "C" (list 3315 625.0) 10 0 "4xUTP")
(command "-LAYER" "S" "Cables_UTP" "")
(command "-COLOR" "5")
(command "_.PLINE" (list 3400 1150) (list 3400 40) (list 3360.0 40) (list 3360.0 20) "")
(command "-LAYER" "S" "Cables_UTP" "")
(command "-COLOR" "5")
(command "-TEXT" "S" "Standard" "J" "C" (list 3415 595.0) 10 0 "4xUTP")
(command "-LAYER" "S" "Cables_UTP" "")
(command "-COLOR" "5")
(command "_.PLINE" (list 3500 1150) (list 3500 -20) (list 3360.0 -20) (list 3360.0 -40) "")
(command "-LAYER" "S" "Cables_UTP" "")
(command "-COLOR" "5")
(command "-TEXT" "S" "Standard" "J" "C" (list 3515 565.0) 10 0 "2xUTP")
(command "-LAYER" "S" "Cables_UTP" "")
(command "-COLOR" "5")
(command "_.PLINE" (list 3600 1150) (list 3600 -140) (list 3360.0 -140) (list 3360.0 -160) "")
(command "-LAYER" "S" "Cables_UTP" "")
(command "-COLOR" "5")
(command "-TEXT" "S" "Standard" "J" "C" (list 3615 505.0) 10 0 "1xUTP")
(command "-LAYER" "S" "Cables_UTP" "")
(command "-COLOR" "5")
(command "_.PLINE" (list 3700 1150) (list 3700 -80) (list 3360.0 -80) (list 3360.0 -100) "")
(command "-LAYER" "S" "Cables_UTP" "")
(command "-COLOR" "5")
(command "-TEXT" "S" "Standard" "J" "C" (list 3715 535.0) 10 0 "10xUTP")
(command "-LAYER" "S" "Cables_UTP" "")
(command "-COLOR" "5")
(command "_.PLINE" (list 3300 1350) (list 3300 100) (list 3360.0 100) (list 3360.0 80) "")
(command "-LAYER" "S" "Cables_UTP" "")
(command "-COLOR" "5")
(command "-TEXT" "S" "Standard" "J" "C" (list 3315 725.0) 10 0 "4xUTP")
(command "-LAYER" "S" "Cables_UTP" "")
(command "-COLOR" "5")
(command "_.PLINE" (list 3400 1350) (list 3400 40) (list 3360.0 40) (list 3360.0 20) "")
(command "-LAYER" "S" "Cables_UTP" "")
(command "-COLOR" "5")
(command "-TEXT" "S" "Standard" "J" "C" (list 3415 695.0) 10 0 "4xUTP")
(command "-LAYER" "S" "Cables_UTP" "")
(command "-COLOR" "5")
(command "_.PLINE" (list 3500 1350) (list 3500 -20) (list 3360.0 -20) (list 3360.0 -40) "")
(command "-LAYER" "S" "Cables_UTP" "")
(command "-COLOR" "5")
(command "-TEXT" "S" "Standard" "J" "C" (list 3515 665.0) 10 0 "2xUTP")
(command "-LAYER" "S" "Cables_UTP" "")
(command "-COLOR" "5")
(command "_.PLINE" (list 3600 1350) (list 3600 -140) (list 3360.0 -140) (list 3360.0 -160) "")
(command "-LAYER" "S" "Cables_UTP" "")
(command "-COLOR" "5")
(command "-TEXT" "S" "Standard" "J" "C" (list 3615 605.0) 10 0 "1xUTP")
(command "-LAYER" "S" "Cables_UTP" "")
(command "-COLOR" "5")
(command "_.PLINE" (list 3700 1350) (list 3700 -80) (list 3360.0 -80) (list 3360.0 -100) "")
(command "-LAYER" "S" "Cables_UTP" "")
(command "-COLOR" "5")
(command "-TEXT" "S" "Standard" "J" "C" (list 3715 635.0) 10 0 "10xUTP")
(command "-LAYER" "S" "Cables_UTP" "")
(command "-COLOR" "5")
(command "_.PLINE" (list 3300 1550) (list 3300 100) (list 3360.0 100) (list 3360.0 80) "")
(command "-LAYER" "S" "Cables_UTP" "")
(command "-COLOR" "5")
(command "-TEXT" "S" "Standard" "J" "C" (list 3315 825.0) 10 0 "2xUTP")
(command "-LAYER" "S" "Cables_UTP" "")
(command "-COLOR" "5")
(command "_.PLINE" (list 3400 1550) (list 3400 40) (list 3360.0 40) (list 3360.0 20) "")
(command "-LAYER" "S" "Cables_UTP" "")
(command "-COLOR" "5")
(command "-TEXT" "S" "Standard" "J" "C" (list 3415 795.0) 10 0 "2xUTP")
(command "-LAYER" "S" "Cables_UTP" "")
(command "-COLOR" "5")
(command "_.PLINE" (list 3500 1550) (list 3500 -20) (list 3360.0 -20) (list 3360.0 -40) "")
(command "-LAYER" "S" "Cables_UTP" "")
(command "-COLOR" "5")
(command "-TEXT" "S" "Standard" "J" "C" (list 3515 765.0) 10 0 "1xUTP")
(command "-LAYER" "S" "Cables_UTP" "")
(command "-COLOR" "5")
(command "_.PLINE" (list 3600 1550) (list 3600 -140) (list 3360.0 -140) (list 3360.0 -160) "")
(command "-LAYER" "S" "Cables_UTP" "")
(command "-COLOR" "5")
(command "-TEXT" "S" "Standard" "J" "C" (list 3615 705.0) 10 0 "1xUTP")
(command "-LAYER" "S" "Cables_UTP" "")
(command "-COLOR" "5")
(command "_.PLINE" (list 3700 1550) (list 3700 -80) (list 3360.0 -80) (list 3360.0 -100) "")
(command "-LAYER" "S" "Cables_UTP" "")
(command "-COLOR" "5")
(command "-TEXT" "S" "Standard" "J" "C" (list 3715 735.0) 10 0 "6xUTP")
(command "-LAYER" "S" "Cables_UTP" "")
(command "-COLOR" "5")
(command "_.PLINE" (list 4350 150) (list 4350 40) (list 4410.0 40) (list 4410.0 20) "")
(command "-LAYER" "S" "Cables_UTP" "")
(command "-COLOR" "5")
(command "-TEXT" "S" "Standard" "J" "C" (list 4365 95.0) 10 0 "1xUTP")
(command "-LAYER" "S" "Cables_UTP" "")
(command "-COLOR" "5")
(command "_.PLINE" (list 4450 150) (list 4450 -140) (list 4410.0 -140) (list 4410.0 -160) "")
(command "-LAYER" "S" "Cables_UTP" "")
(command "-COLOR" "5")
(command "-TEXT" "S" "Standard" "J" "C" (list 4465 5.0) 10 0 "1xUTP")
(command "-LAYER" "S" "Cables_UTP" "")
(command "-COLOR" "5")
(command "_.PLINE" (list 4550 150) (list 4550 -80) (list 4410.0 -80) (list 4410.0 -100) "")
(command "-LAYER" "S" "Cables_UTP" "")
(command "-COLOR" "5")
(command "-TEXT" "S" "Standard" "J" "C" (list 4565 35.0) 10 0 "3xUTP")
(command "-LAYER" "S" "Cables_UTP" "")
(command "-COLOR" "5")
(command "_.PLINE" (list 4350 350) (list 4350 100) (list 4410.0 100) (list 4410.0 80) "")
(command "-LAYER" "S" "Cables_UTP" "")
(command "-COLOR" "5")
(command "-TEXT" "S" "Standard" "J" "C" (list 4365 225.0) 10 0 "3xUTP")
(command "-LAYER" "S" "Cables_UTP" "")
(command "-COLOR" "5")
(command "_.PLINE" (list 4450 350) (list 4450 40) (list 4410.0 40) (list 4410.0 20) "")
(command "-LAYER" "S" "Cables_UTP" "")
(command "-COLOR" "5")
(command "-TEXT" "S" "Standard" "J" "C" (list 4465 195.0) 10 0 "4xUTP")
(command "-LAYER" "S" "Cables_UTP" "")
(command "-COLOR" "5")
(command "_.PLINE" (list 4550 350) (list 4550 -20) (list 4410.0 -20) (list 4410.0 -40) "")
(command "-LAYER" "S" "Cables_UTP" "")
(command "-COLOR" "5")
(command "-TEXT" "S" "Standard" "J" "C" (list 4565 165.0) 10 0 "2xUTP")
(command "-LAYER" "S" "Cables_UTP" "")
(command "-COLOR" "5")
(command "_.PLINE" (list 4650 350) (list 4650 -140) (list 4410.0 -140) (list 4410.0 -160) "")
(command "-LAYER" "S" "Cables_UTP" "")
(command "-COLOR" "5")
(command "-TEXT" "S" "Standard" "J" "C" (list 4665 105.0) 10 0 "1xUTP")
(command "-LAYER" "S" "Cables_UTP" "")
(command "-COLOR" "5")
(command "_.PLINE" (list 4750 350) (list 4750 -80) (list 4410.0 -80) (list 4410.0 -100) "")
(command "-LAYER" "S" "Cables_UTP" "")
(command "-COLOR" "5")
(command "-TEXT" "S" "Standard" "J" "C" (list 4765 135.0) 10 0 "8xUTP")
(command "-LAYER" "S" "Cables_UTP" "")
(command "-COLOR" "5")
(command "_.PLINE" (list 4350 550) (list 4350 100) (list 4410.0 100) (list 4410.0 80) "")
(command "-LAYER" "S" "Cables_UTP" "")
(command "-COLOR" "5")
(command "-TEXT" "S" "Standard" "J" "C" (list 4365 325.0) 10 0 "3xUTP")
(command "-LAYER" "S" "Cables_UTP" "")
(command "-COLOR" "5")
(command "_.PLINE" (list 4450 550) (list 4450 40) (list 4410.0 40) (list 4410.0 20) "")
(command "-LAYER" "S" "Cables_UTP" "")
(command "-COLOR" "5")
(command "-TEXT" "S" "Standard" "J" "C" (list 4465 295.0) 10 0 "3xUTP")
(command "-LAYER" "S" "Cables_UTP" "")
(command "-COLOR" "5")
(command "_.PLINE" (list 4550 550) (list 4550 -20) (list 4410.0 -20) (list 4410.0 -40) "")
(command "-LAYER" "S" "Cables_UTP" "")
(command "-COLOR" "5")
(command "-TEXT" "S" "Standard" "J" "C" (list 4565 265.0) 10 0 "1xUTP")
(command "-LAYER" "S" "Cables_UTP" "")
(command "-COLOR" "5")
(command "_.PLINE" (list 4650 550) (list 4650 -140) (list 4410.0 -140) (list 4410.0 -160) "")
(command "-LAYER" "S" "Cables_UTP" "")
(command "-COLOR" "5")
(command "-TEXT" "S" "Standard" "J" "C" (list 4665 205.0) 10 0 "1xUTP")
(command "-LAYER" "S" "Cables_UTP" "")
(command "-COLOR" "5")
(command "_.PLINE" (list 4750 550) (list 4750 -80) (list 4410.0 -80) (list 4410.0 -100) "")
(command "-LAYER" "S" "Cables_UTP" "")
(command "-COLOR" "5")
(command "-TEXT" "S" "Standard" "J" "C" (list 4765 235.0) 10 0 "7xUTP")
(command "-LAYER" "S" "Cables_UTP" "")
(command "-COLOR" "5")
(command "_.PLINE" (list 4350 750) (list 4350 100) (list 4410.0 100) (list 4410.0 80) "")
(command "-LAYER" "S" "Cables_UTP" "")
(command "-COLOR" "5")
(command "-TEXT" "S" "Standard" "J" "C" (list 4365 425.0) 10 0 "3xUTP")
(command "-LAYER" "S" "Cables_UTP" "")
(command "-COLOR" "5")
(command "_.PLINE" (list 4450 750) (list 4450 40) (list 4410.0 40) (list 4410.0 20) "")
(command "-LAYER" "S" "Cables_UTP" "")
(command "-COLOR" "5")
(command "-TEXT" "S" "Standard" "J" "C" (list 4465 395.0) 10 0 "3xUTP")
(command "-LAYER" "S" "Cables_UTP" "")
(command "-COLOR" "5")
(command "_.PLINE" (list 4550 750) (list 4550 -20) (list 4410.0 -20) (list 4410.0 -40) "")
(command "-LAYER" "S" "Cables_UTP" "")
(command "-COLOR" "5")
(command "-TEXT" "S" "Standard" "J" "C" (list 4565 365.0) 10 0 "1xUTP")
(command "-LAYER" "S" "Cables_UTP" "")
(command "-COLOR" "5")
(command "_.PLINE" (list 4650 750) (list 4650 -140) (list 4410.0 -140) (list 4410.0 -160) "")
(command "-LAYER" "S" "Cables_UTP" "")
(command "-COLOR" "5")
(command "-TEXT" "S" "Standard" "J" "C" (list 4665 305.0) 10 0 "1xUTP")
(command "-LAYER" "S" "Cables_UTP" "")
(command "-COLOR" "5")
(command "_.PLINE" (list 4750 750) (list 4750 -80) (list 4410.0 -80) (list 4410.0 -100) "")
(command "-LAYER" "S" "Cables_UTP" "")
(command "-COLOR" "5")
(command "-TEXT" "S" "Standard" "J" "C" (list 4765 335.0) 10 0 "7xUTP")
(command "-LAYER" "S" "Cables_UTP" "")
(command "-COLOR" "5")
(command "_.PLINE" (list 4350 950) (list 4350 100) (list 4410.0 100) (list 4410.0 80) "")
(command "-LAYER" "S" "Cables_UTP" "")
(command "-COLOR" "5")
(command "-TEXT" "S" "Standard" "J" "C" (list 4365 525.0) 10 0 "3xUTP")
(command "-LAYER" "S" "Cables_UTP" "")
(command "-COLOR" "5")
(command "_.PLINE" (list 4450 950) (list 4450 40) (list 4410.0 40) (list 4410.0 20) "")
(command "-LAYER" "S" "Cables_UTP" "")
(command "-COLOR" "5")
(command "-TEXT" "S" "Standard" "J" "C" (list 4465 495.0) 10 0 "3xUTP")
(command "-LAYER" "S" "Cables_UTP" "")
(command "-COLOR" "5")
(command "_.PLINE" (list 4550 950) (list 4550 -20) (list 4410.0 -20) (list 4410.0 -40) "")
(command "-LAYER" "S" "Cables_UTP" "")
(command "-COLOR" "5")
(command "-TEXT" "S" "Standard" "J" "C" (list 4565 465.0) 10 0 "1xUTP")
(command "-LAYER" "S" "Cables_UTP" "")
(command "-COLOR" "5")
(command "_.PLINE" (list 4650 950) (list 4650 -140) (list 4410.0 -140) (list 4410.0 -160) "")
(command "-LAYER" "S" "Cables_UTP" "")
(command "-COLOR" "5")
(command "-TEXT" "S" "Standard" "J" "C" (list 4665 405.0) 10 0 "1xUTP")
(command "-LAYER" "S" "Cables_UTP" "")
(command "-COLOR" "5")
(command "_.PLINE" (list 4750 950) (list 4750 -80) (list 4410.0 -80) (list 4410.0 -100) "")
(command "-LAYER" "S" "Cables_UTP" "")
(command "-COLOR" "5")
(command "-TEXT" "S" "Standard" "J" "C" (list 4765 435.0) 10 0 "7xUTP")
(command "-LAYER" "S" "Cables_UTP" "")
(command "-COLOR" "5")
(command "_.PLINE" (list 4350 1150) (list 4350 100) (list 4410.0 100) (list 4410.0 80) "")
(command "-LAYER" "S" "Cables_UTP" "")
(command "-COLOR" "5")
(command "-TEXT" "S" "Standard" "J" "C" (list 4365 625.0) 10 0 "3xUTP")
(command "-LAYER" "S" "Cables_UTP" "")
(command "-COLOR" "5")
(command "_.PLINE" (list 4450 1150) (list 4450 40) (list 4410.0 40) (list 4410.0 20) "")
(command "-LAYER" "S" "Cables_UTP" "")
(command "-COLOR" "5")
(command "-TEXT" "S" "Standard" "J" "C" (list 4465 595.0) 10 0 "3xUTP")
(command "-LAYER" "S" "Cables_UTP" "")
(command "-COLOR" "5")
(command "_.PLINE" (list 4550 1150) (list 4550 -20) (list 4410.0 -20) (list 4410.0 -40) "")
(command "-LAYER" "S" "Cables_UTP" "")
(command "-COLOR" "5")
(command "-TEXT" "S" "Standard" "J" "C" (list 4565 565.0) 10 0 "1xUTP")
(command "-LAYER" "S" "Cables_UTP" "")
(command "-COLOR" "5")
(command "_.PLINE" (list 4650 1150) (list 4650 -140) (list 4410.0 -140) (list 4410.0 -160) "")
(command "-LAYER" "S" "Cables_UTP" "")
(command "-COLOR" "5")
(command "-TEXT" "S" "Standard" "J" "C" (list 4665 505.0) 10 0 "1xUTP")
(command "-LAYER" "S" "Cables_UTP" "")
(command "-COLOR" "5")
(command "_.PLINE" (list 4750 1150) (list 4750 -80) (list 4410.0 -80) (list 4410.0 -100) "")
(command "-LAYER" "S" "Cables_UTP" "")
(command "-COLOR" "5")
(command "-TEXT" "S" "Standard" "J" "C" (list 4765 535.0) 10 0 "7xUTP")
(command "-LAYER" "S" "Cables_UTP" "")
(command "-COLOR" "5")
(command "_.PLINE" (list 4350 1350) (list 4350 100) (list 4410.0 100) (list 4410.0 80) "")
(command "-LAYER" "S" "Cables_UTP" "")
(command "-COLOR" "5")
(command "-TEXT" "S" "Standard" "J" "C" (list 4365 725.0) 10 0 "3xUTP")
(command "-LAYER" "S" "Cables_UTP" "")
(command "-COLOR" "5")
(command "_.PLINE" (list 4450 1350) (list 4450 40) (list 4410.0 40) (list 4410.0 20) "")
(command "-LAYER" "S" "Cables_UTP" "")
(command "-COLOR" "5")
(command "-TEXT" "S" "Standard" "J" "C" (list 4465 695.0) 10 0 "3xUTP")
(command "-LAYER" "S" "Cables_UTP" "")
(command "-COLOR" "5")
(command "_.PLINE" (list 4550 1350) (list 4550 -20) (list 4410.0 -20) (list 4410.0 -40) "")
(command "-LAYER" "S" "Cables_UTP" "")
(command "-COLOR" "5")
(command "-TEXT" "S" "Standard" "J" "C" (list 4565 665.0) 10 0 "1xUTP")
(command "-LAYER" "S" "Cables_UTP" "")
(command "-COLOR" "5")
(command "_.PLINE" (list 4650 1350) (list 4650 -140) (list 4410.0 -140) (list 4410.0 -160) "")
(command "-LAYER" "S" "Cables_UTP" "")
(command "-COLOR" "5")
(command "-TEXT" "S" "Standard" "J" "C" (list 4665 605.0) 10 0 "1xUTP")
(command "-LAYER" "S" "Cables_UTP" "")
(command "-COLOR" "5")
(command "_.PLINE" (list 4750 1350) (list 4750 -80) (list 4410.0 -80) (list 4410.0 -100) "")
(command "-LAYER" "S" "Cables_UTP" "")
(command "-COLOR" "5")
(command "-TEXT" "S" "Standard" "J" "C" (list 4765 635.0) 10 0 "7xUTP")
(command "-LAYER" "S" "Cables_UTP" "")
(command "-COLOR" "5")
(command "_.PLINE" (list 4350 1550) (list 4350 100) (list 4410.0 100) (list 4410.0 80) "")
(command "-LAYER" "S" "Cables_UTP" "")
(command "-COLOR" "5")
(command "-TEXT" "S" "Standard" "J" "C" (list 4365 825.0) 10 0 "2xUTP")
(command "-LAYER" "S" "Cables_UTP" "")
(command "-COLOR" "5")
(command "_.PLINE" (list 4450 1550) (list 4450 40) (list 4410.0 40) (list 4410.0 20) "")
(command "-LAYER" "S" "Cables_UTP" "")
(command "-COLOR" "5")
(command "-TEXT" "S" "Standard" "J" "C" (list 4465 795.0) 10 0 "2xUTP")
(command "-LAYER" "S" "Cables_UTP" "")
(command "-COLOR" "5")
(command "_.PLINE" (list 4550 1550) (list 4550 -20) (list 4410.0 -20) (list 4410.0 -40) "")
(command "-LAYER" "S" "Cables_UTP" "")
(command "-COLOR" "5")
(command "-TEXT" "S" "Standard" "J" "C" (list 4565 765.0) 10 0 "1xUTP")
(command "-LAYER" "S" "Cables_UTP" "")
(command "-COLOR" "5")
(command "_.PLINE" (list 4650 1550) (list 4650 -140) (list 4410.0 -140) (list 4410.0 -160) "")
(command "-LAYER" "S" "Cables_UTP" "")
(command "-COLOR" "5")
(command "-TEXT" "S" "Standard" "J" "C" (list 4665 705.0) 10 0 "1xUTP")
(command "-LAYER" "S" "Cables_UTP" "")
(command "-COLOR" "5")
(command "_.PLINE" (list 4750 1550) (list 4750 -80) (list 4410.0 -80) (list 4410.0 -100) "")
(command "-LAYER" "S" "Cables_UTP" "")
(command "-COLOR" "5")
(command "-TEXT" "S" "Standard" "J" "C" (list 4765 735.0) 10 0 "6xUTP")
(command "-LAYER" "S" "Cables_UTP" "")
(command "-COLOR" "5")
(command "_.PLINE" (list 5400 150) (list 5400 100) (list 5460.0 100) (list 5460.0 80) "")
(command "-LAYER" "S" "Cables_UTP" "")
(command "-COLOR" "5")
(command "-TEXT" "S" "Standard" "J" "C" (list 5415 125.0) 10 0 "1xUTP")
(command "-LAYER" "S" "Cables_UTP" "")
(command "-COLOR" "5")
(command "_.PLINE" (list 5500 150) (list 5500 40) (list 5460.0 40) (list 5460.0 20) "")
(command "-LAYER" "S" "Cables_UTP" "")
(command "-COLOR" "5")
(command "-TEXT" "S" "Standard" "J" "C" (list 5515 95.0) 10 0 "2xUTP")
(command "-LAYER" "S" "Cables_UTP" "")
(command "-COLOR" "5")
(command "_.PLINE" (list 5600 150) (list 5600 -20) (list 5460.0 -20) (list 5460.0 -40) "")
(command "-LAYER" "S" "Cables_UTP" "")
(command "-COLOR" "5")
(command "-TEXT" "S" "Standard" "J" "C" (list 5615 65.0) 10 0 "1xUTP")
(command "-LAYER" "S" "Cables_UTP" "")
(command "-COLOR" "5")
(command "_.PLINE" (list 5700 150) (list 5700 -140) (list 5460.0 -140) (list 5460.0 -160) "")
(command "-LAYER" "S" "Cables_UTP" "")
(command "-COLOR" "5")
(command "-TEXT" "S" "Standard" "J" "C" (list 5715 5.0) 10 0 "1xUTP")
(command "-LAYER" "S" "Cables_UTP" "")
(command "-COLOR" "5")
(command "_.PLINE" (list 5800 150) (list 5800 -80) (list 5460.0 -80) (list 5460.0 -100) "")
(command "-LAYER" "S" "Cables_UTP" "")
(command "-COLOR" "5")
(command "-TEXT" "S" "Standard" "J" "C" (list 5815 35.0) 10 0 "5xUTP")
(command "-LAYER" "S" "Cables_UTP" "")
(command "-COLOR" "5")
(command "_.PLINE" (list 5400 350) (list 5400 100) (list 5460.0 100) (list 5460.0 80) "")
(command "-LAYER" "S" "Cables_UTP" "")
(command "-COLOR" "5")
(command "-TEXT" "S" "Standard" "J" "C" (list 5415 225.0) 10 0 "4xUTP")
(command "-LAYER" "S" "Cables_UTP" "")
(command "-COLOR" "5")
(command "_.PLINE" (list 5500 350) (list 5500 40) (list 5460.0 40) (list 5460.0 20) "")
(command "-LAYER" "S" "Cables_UTP" "")
(command "-COLOR" "5")
(command "-TEXT" "S" "Standard" "J" "C" (list 5515 195.0) 10 0 "5xUTP")
(command "-LAYER" "S" "Cables_UTP" "")
(command "-COLOR" "5")
(command "_.PLINE" (list 5600 350) (list 5600 -20) (list 5460.0 -20) (list 5460.0 -40) "")
(command "-LAYER" "S" "Cables_UTP" "")
(command "-COLOR" "5")
(command "-TEXT" "S" "Standard" "J" "C" (list 5615 165.0) 10 0 "3xUTP")
(command "-LAYER" "S" "Cables_UTP" "")
(command "-COLOR" "5")
(command "_.PLINE" (list 5700 350) (list 5700 -140) (list 5460.0 -140) (list 5460.0 -160) "")
(command "-LAYER" "S" "Cables_UTP" "")
(command "-COLOR" "5")
(command "-TEXT" "S" "Standard" "J" "C" (list 5715 105.0) 10 0 "2xUTP")
(command "-LAYER" "S" "Cables_UTP" "")
(command "-COLOR" "5")
(command "_.PLINE" (list 5800 350) (list 5800 -80) (list 5460.0 -80) (list 5460.0 -100) "")
(command "-LAYER" "S" "Cables_UTP" "")
(command "-COLOR" "5")
(command "-TEXT" "S" "Standard" "J" "C" (list 5815 135.0) 10 0 "12xUTP")
(command "-LAYER" "S" "Cables_UTP" "")
(command "-COLOR" "5")
(command "_.PLINE" (list 5400 550) (list 5400 100) (list 5460.0 100) (list 5460.0 80) "")
(command "-LAYER" "S" "Cables_UTP" "")
(command "-COLOR" "5")
(command "-TEXT" "S" "Standard" "J" "C" (list 5415 325.0) 10 0 "4xUTP")
(command "-LAYER" "S" "Cables_UTP" "")
(command "-COLOR" "5")
(command "_.PLINE" (list 5500 550) (list 5500 40) (list 5460.0 40) (list 5460.0 20) "")
(command "-LAYER" "S" "Cables_UTP" "")
(command "-COLOR" "5")
(command "-TEXT" "S" "Standard" "J" "C" (list 5515 295.0) 10 0 "4xUTP")
(command "-LAYER" "S" "Cables_UTP" "")
(command "-COLOR" "5")
(command "_.PLINE" (list 5600 550) (list 5600 -20) (list 5460.0 -20) (list 5460.0 -40) "")
(command "-LAYER" "S" "Cables_UTP" "")
(command "-COLOR" "5")
(command "-TEXT" "S" "Standard" "J" "C" (list 5615 265.0) 10 0 "2xUTP")
(command "-LAYER" "S" "Cables_UTP" "")
(command "-COLOR" "5")
(command "_.PLINE" (list 5700 550) (list 5700 -140) (list 5460.0 -140) (list 5460.0 -160) "")
(command "-LAYER" "S" "Cables_UTP" "")
(command "-COLOR" "5")
(command "-TEXT" "S" "Standard" "J" "C" (list 5715 205.0) 10 0 "1xUTP")
(command "-LAYER" "S" "Cables_UTP" "")
(command "-COLOR" "5")
(command "_.PLINE" (list 5800 550) (list 5800 -80) (list 5460.0 -80) (list 5460.0 -100) "")
(command "-LAYER" "S" "Cables_UTP" "")
(command "-COLOR" "5")
(command "-TEXT" "S" "Standard" "J" "C" (list 5815 235.0) 10 0 "10xUTP")
(command "-LAYER" "S" "Cables_UTP" "")
(command "-COLOR" "5")
(command "_.PLINE" (list 5400 750) (list 5400 100) (list 5460.0 100) (list 5460.0 80) "")
(command "-LAYER" "S" "Cables_UTP" "")
(command "-COLOR" "5")
(command "-TEXT" "S" "Standard" "J" "C" (list 5415 425.0) 10 0 "4xUTP")
(command "-LAYER" "S" "Cables_UTP" "")
(command "-COLOR" "5")
(command "_.PLINE" (list 5500 750) (list 5500 40) (list 5460.0 40) (list 5460.0 20) "")
(command "-LAYER" "S" "Cables_UTP" "")
(command "-COLOR" "5")
(command "-TEXT" "S" "Standard" "J" "C" (list 5515 395.0) 10 0 "4xUTP")
(command "-LAYER" "S" "Cables_UTP" "")
(command "-COLOR" "5")
(command "_.PLINE" (list 5600 750) (list 5600 -20) (list 5460.0 -20) (list 5460.0 -40) "")
(command "-LAYER" "S" "Cables_UTP" "")
(command "-COLOR" "5")
(command "-TEXT" "S" "Standard" "J" "C" (list 5615 365.0) 10 0 "2xUTP")
(command "-LAYER" "S" "Cables_UTP" "")
(command "-COLOR" "5")
(command "_.PLINE" (list 5700 750) (list 5700 -140) (list 5460.0 -140) (list 5460.0 -160) "")
(command "-LAYER" "S" "Cables_UTP" "")
(command "-COLOR" "5")
(command "-TEXT" "S" "Standard" "J" "C" (list 5715 305.0) 10 0 "1xUTP")
(command "-LAYER" "S" "Cables_UTP" "")
(command "-COLOR" "5")
(command "_.PLINE" (list 5800 750) (list 5800 -80) (list 5460.0 -80) (list 5460.0 -100) "")
(command "-LAYER" "S" "Cables_UTP" "")
(command "-COLOR" "5")
(command "-TEXT" "S" "Standard" "J" "C" (list 5815 335.0) 10 0 "10xUTP")
(command "-LAYER" "S" "Cables_UTP" "")
(command "-COLOR" "5")
(command "_.PLINE" (list 5400 950) (list 5400 100) (list 5460.0 100) (list 5460.0 80) "")
(command "-LAYER" "S" "Cables_UTP" "")
(command "-COLOR" "5")
(command "-TEXT" "S" "Standard" "J" "C" (list 5415 525.0) 10 0 "4xUTP")
(command "-LAYER" "S" "Cables_UTP" "")
(command "-COLOR" "5")
(command "_.PLINE" (list 5500 950) (list 5500 40) (list 5460.0 40) (list 5460.0 20) "")
(command "-LAYER" "S" "Cables_UTP" "")
(command "-COLOR" "5")
(command "-TEXT" "S" "Standard" "J" "C" (list 5515 495.0) 10 0 "4xUTP")
(command "-LAYER" "S" "Cables_UTP" "")
(command "-COLOR" "5")
(command "_.PLINE" (list 5600 950) (list 5600 -20) (list 5460.0 -20) (list 5460.0 -40) "")
(command "-LAYER" "S" "Cables_UTP" "")
(command "-COLOR" "5")
(command "-TEXT" "S" "Standard" "J" "C" (list 5615 465.0) 10 0 "2xUTP")
(command "-LAYER" "S" "Cables_UTP" "")
(command "-COLOR" "5")
(command "_.PLINE" (list 5700 950) (list 5700 -140) (list 5460.0 -140) (list 5460.0 -160) "")
(command "-LAYER" "S" "Cables_UTP" "")
(command "-COLOR" "5")
(command "-TEXT" "S" "Standard" "J" "C" (list 5715 405.0) 10 0 "1xUTP")
(command "-LAYER" "S" "Cables_UTP" "")
(command "-COLOR" "5")
(command "_.PLINE" (list 5800 950) (list 5800 -80) (list 5460.0 -80) (list 5460.0 -100) "")
(command "-LAYER" "S" "Cables_UTP" "")
(command "-COLOR" "5")
(command "-TEXT" "S" "Standard" "J" "C" (list 5815 435.0) 10 0 "10xUTP")
(command "-LAYER" "S" "Cables_UTP" "")
(command "-COLOR" "5")
(command "_.PLINE" (list 5400 1150) (list 5400 100) (list 5460.0 100) (list 5460.0 80) "")
(command "-LAYER" "S" "Cables_UTP" "")
(command "-COLOR" "5")
(command "-TEXT" "S" "Standard" "J" "C" (list 5415 625.0) 10 0 "4xUTP")
(command "-LAYER" "S" "Cables_UTP" "")
(command "-COLOR" "5")
(command "_.PLINE" (list 5500 1150) (list 5500 40) (list 5460.0 40) (list 5460.0 20) "")
(command "-LAYER" "S" "Cables_UTP" "")
(command "-COLOR" "5")
(command "-TEXT" "S" "Standard" "J" "C" (list 5515 595.0) 10 0 "4xUTP")
(command "-LAYER" "S" "Cables_UTP" "")
(command "-COLOR" "5")
(command "_.PLINE" (list 5600 1150) (list 5600 -20) (list 5460.0 -20) (list 5460.0 -40) "")
(command "-LAYER" "S" "Cables_UTP" "")
(command "-COLOR" "5")
(command "-TEXT" "S" "Standard" "J" "C" (list 5615 565.0) 10 0 "2xUTP")
(command "-LAYER" "S" "Cables_UTP" "")
(command "-COLOR" "5")
(command "_.PLINE" (list 5700 1150) (list 5700 -140) (list 5460.0 -140) (list 5460.0 -160) "")
(command "-LAYER" "S" "Cables_UTP" "")
(command "-COLOR" "5")
(command "-TEXT" "S" "Standard" "J" "C" (list 5715 505.0) 10 0 "1xUTP")
(command "-LAYER" "S" "Cables_UTP" "")
(command "-COLOR" "5")
(command "_.PLINE" (list 5800 1150) (list 5800 -80) (list 5460.0 -80) (list 5460.0 -100) "")
(command "-LAYER" "S" "Cables_UTP" "")
(command "-COLOR" "5")
(command "-TEXT" "S" "Standard" "J" "C" (list 5815 535.0) 10 0 "10xUTP")
(command "-LAYER" "S" "Cables_UTP" "")
(command "-COLOR" "5")
(command "_.PLINE" (list 5400 1350) (list 5400 100) (list 5460.0 100) (list 5460.0 80) "")
(command "-LAYER" "S" "Cables_UTP" "")
(command "-COLOR" "5")
(command "-TEXT" "S" "Standard" "J" "C" (list 5415 725.0) 10 0 "4xUTP")
(command "-LAYER" "S" "Cables_UTP" "")
(command "-COLOR" "5")
(command "_.PLINE" (list 5500 1350) (list 5500 40) (list 5460.0 40) (list 5460.0 20) "")
(command "-LAYER" "S" "Cables_UTP" "")
(command "-COLOR" "5")
(command "-TEXT" "S" "Standard" "J" "C" (list 5515 695.0) 10 0 "4xUTP")
(command "-LAYER" "S" "Cables_UTP" "")
(command "-COLOR" "5")
(command "_.PLINE" (list 5600 1350) (list 5600 -20) (list 5460.0 -20) (list 5460.0 -40) "")
(command "-LAYER" "S" "Cables_UTP" "")
(command "-COLOR" "5")
(command "-TEXT" "S" "Standard" "J" "C" (list 5615 665.0) 10 0 "2xUTP")
(command "-LAYER" "S" "Cables_UTP" "")
(command "-COLOR" "5")
(command "_.PLINE" (list 5700 1350) (list 5700 -140) (list 5460.0 -140) (list 5460.0 -160) "")
(command "-LAYER" "S" "Cables_UTP" "")
(command "-COLOR" "5")
(command "-TEXT" "S" "Standard" "J" "C" (list 5715 605.0) 10 0 "1xUTP")
(command "-LAYER" "S" "Cables_UTP" "")
(command "-COLOR" "5")
(command "_.PLINE" (list 5800 1350) (list 5800 -80) (list 5460.0 -80) (list 5460.0 -100) "")
(command "-LAYER" "S" "Cables_UTP" "")
(command "-COLOR" "5")
(command "-TEXT" "S" "Standard" "J" "C" (list 5815 635.0) 10 0 "10xUTP")
(command "-LAYER" "S" "Cables_UTP" "")
(command "-COLOR" "5")
(command "_.PLINE" (list 5400 1550) (list 5400 100) (list 5460.0 100) (list 5460.0 80) "")
(command "-LAYER" "S" "Cables_UTP" "")
(command "-COLOR" "5")
(command "-TEXT" "S" "Standard" "J" "C" (list 5415 825.0) 10 0 "2xUTP")
(command "-LAYER" "S" "Cables_UTP" "")
(command "-COLOR" "5")
(command "_.PLINE" (list 5500 1550) (list 5500 40) (list 5460.0 40) (list 5460.0 20) "")
(command "-LAYER" "S" "Cables_UTP" "")
(command "-COLOR" "5")
(command "-TEXT" "S" "Standard" "J" "C" (list 5515 795.0) 10 0 "2xUTP")
(command "-LAYER" "S" "Cables_UTP" "")
(command "-COLOR" "5")
(command "_.PLINE" (list 5600 1550) (list 5600 -20) (list 5460.0 -20) (list 5460.0 -40) "")
(command "-LAYER" "S" "Cables_UTP" "")
(command "-COLOR" "5")
(command "-TEXT" "S" "Standard" "J" "C" (list 5615 765.0) 10 0 "1xUTP")
(command "-LAYER" "S" "Cables_UTP" "")
(command "-COLOR" "5")
(command "_.PLINE" (list 5700 1550) (list 5700 -140) (list 5460.0 -140) (list 5460.0 -160) "")
(command "-LAYER" "S" "Cables_UTP" "")
(command "-COLOR" "5")
(command "-TEXT" "S" "Standard" "J" "C" (list 5715 705.0) 10 0 "1xUTP")
(command "-LAYER" "S" "Cables_UTP" "")
(command "-COLOR" "5")
(command "_.PLINE" (list 5800 1550) (list 5800 -80) (list 5460.0 -80) (list 5460.0 -100) "")
(command "-LAYER" "S" "Cables_UTP" "")
(command "-COLOR" "5")
(command "-TEXT" "S" "Standard" "J" "C" (list 5815 735.0) 10 0 "6xUTP")
(command "-LAYER" "S" "Cables_UTP" "")
(command "-COLOR" "5")
(command "_.PLINE" (list 6450 150) (list 6450 100) (list 6510.0 100) (list 6510.0 80) "")
(command "-LAYER" "S" "Cables_UTP" "")
(command "-COLOR" "5")
(command "-TEXT" "S" "Standard" "J" "C" (list 6465 125.0) 10 0 "2xUTP")
(command "-LAYER" "S" "Cables_UTP" "")
(command "-COLOR" "5")
(command "_.PLINE" (list 6550 150) (list 6550 40) (list 6510.0 40) (list 6510.0 20) "")
(command "-LAYER" "S" "Cables_UTP" "")
(command "-COLOR" "5")
(command "-TEXT" "S" "Standard" "J" "C" (list 6565 95.0) 10 0 "3xUTP")
(command "-LAYER" "S" "Cables_UTP" "")
(command "-COLOR" "5")
(command "_.PLINE" (list 6650 150) (list 6650 -20) (list 6510.0 -20) (list 6510.0 -40) "")
(command "-LAYER" "S" "Cables_UTP" "")
(command "-COLOR" "5")
(command "-TEXT" "S" "Standard" "J" "C" (list 6665 65.0) 10 0 "2xUTP")
(command "-LAYER" "S" "Cables_UTP" "")
(command "-COLOR" "5")
(command "_.PLINE" (list 6750 150) (list 6750 -140) (list 6510.0 -140) (list 6510.0 -160) "")
(command "-LAYER" "S" "Cables_UTP" "")
(command "-COLOR" "5")
(command "-TEXT" "S" "Standard" "J" "C" (list 6765 5.0) 10 0 "1xUTP")
(command "-LAYER" "S" "Cables_UTP" "")
(command "-COLOR" "5")
(command "_.PLINE" (list 6850 150) (list 6850 -80) (list 6510.0 -80) (list 6510.0 -100) "")
(command "-LAYER" "S" "Cables_UTP" "")
(command "-COLOR" "5")
(command "-TEXT" "S" "Standard" "J" "C" (list 6865 35.0) 10 0 "7xUTP")
(command "-LAYER" "S" "Cables_UTP" "")
(command "-COLOR" "5")
(command "_.PLINE" (list 6450 350) (list 6450 100) (list 6510.0 100) (list 6510.0 80) "")
(command "-LAYER" "S" "Cables_UTP" "")
(command "-COLOR" "5")
(command "-TEXT" "S" "Standard" "J" "C" (list 6465 225.0) 10 0 "5xUTP")
(command "-LAYER" "S" "Cables_UTP" "")
(command "-COLOR" "5")
(command "_.PLINE" (list 6550 350) (list 6550 40) (list 6510.0 40) (list 6510.0 20) "")
(command "-LAYER" "S" "Cables_UTP" "")
(command "-COLOR" "5")
(command "-TEXT" "S" "Standard" "J" "C" (list 6565 195.0) 10 0 "6xUTP")
(command "-LAYER" "S" "Cables_UTP" "")
(command "-COLOR" "5")
(command "_.PLINE" (list 6650 350) (list 6650 -20) (list 6510.0 -20) (list 6510.0 -40) "")
(command "-LAYER" "S" "Cables_UTP" "")
(command "-COLOR" "5")
(command "-TEXT" "S" "Standard" "J" "C" (list 6665 165.0) 10 0 "4xUTP")
(command "-LAYER" "S" "Cables_UTP" "")
(command "-COLOR" "5")
(command "_.PLINE" (list 6750 350) (list 6750 -140) (list 6510.0 -140) (list 6510.0 -160) "")
(command "-LAYER" "S" "Cables_UTP" "")
(command "-COLOR" "5")
(command "-TEXT" "S" "Standard" "J" "C" (list 6765 105.0) 10 0 "2xUTP")
(command "-LAYER" "S" "Cables_UTP" "")
(command "-COLOR" "5")
(command "_.PLINE" (list 6850 350) (list 6850 -80) (list 6510.0 -80) (list 6510.0 -100) "")
(command "-LAYER" "S" "Cables_UTP" "")
(command "-COLOR" "5")
(command "-TEXT" "S" "Standard" "J" "C" (list 6865 135.0) 10 0 "14xUTP")
(command "-LAYER" "S" "Cables_UTP" "")
(command "-COLOR" "5")
(command "_.PLINE" (list 6450 550) (list 6450 100) (list 6510.0 100) (list 6510.0 80) "")
(command "-LAYER" "S" "Cables_UTP" "")
(command "-COLOR" "5")
(command "-TEXT" "S" "Standard" "J" "C" (list 6465 325.0) 10 0 "4xUTP")
(command "-LAYER" "S" "Cables_UTP" "")
(command "-COLOR" "5")
(command "_.PLINE" (list 6550 550) (list 6550 40) (list 6510.0 40) (list 6510.0 20) "")
(command "-LAYER" "S" "Cables_UTP" "")
(command "-COLOR" "5")
(command "-TEXT" "S" "Standard" "J" "C" (list 6565 295.0) 10 0 "4xUTP")
(command "-LAYER" "S" "Cables_UTP" "")
(command "-COLOR" "5")
(command "_.PLINE" (list 6650 550) (list 6650 -20) (list 6510.0 -20) (list 6510.0 -40) "")
(command "-LAYER" "S" "Cables_UTP" "")
(command "-COLOR" "5")
(command "-TEXT" "S" "Standard" "J" "C" (list 6665 265.0) 10 0 "2xUTP")
(command "-LAYER" "S" "Cables_UTP" "")
(command "-COLOR" "5")
(command "_.PLINE" (list 6750 550) (list 6750 -140) (list 6510.0 -140) (list 6510.0 -160) "")
(command "-LAYER" "S" "Cables_UTP" "")
(command "-COLOR" "5")
(command "-TEXT" "S" "Standard" "J" "C" (list 6765 205.0) 10 0 "1xUTP")
(command "-LAYER" "S" "Cables_UTP" "")
(command "-COLOR" "5")
(command "_.PLINE" (list 6850 550) (list 6850 -80) (list 6510.0 -80) (list 6510.0 -100) "")
(command "-LAYER" "S" "Cables_UTP" "")
(command "-COLOR" "5")
(command "-TEXT" "S" "Standard" "J" "C" (list 6865 235.0) 10 0 "10xUTP")
(command "-LAYER" "S" "Cables_UTP" "")
(command "-COLOR" "5")
(command "_.PLINE" (list 6450 750) (list 6450 100) (list 6510.0 100) (list 6510.0 80) "")
(command "-LAYER" "S" "Cables_UTP" "")
(command "-COLOR" "5")
(command "-TEXT" "S" "Standard" "J" "C" (list 6465 425.0) 10 0 "4xUTP")
(command "-LAYER" "S" "Cables_UTP" "")
(command "-COLOR" "5")
(command "_.PLINE" (list 6550 750) (list 6550 40) (list 6510.0 40) (list 6510.0 20) "")
(command "-LAYER" "S" "Cables_UTP" "")
(command "-COLOR" "5")
(command "-TEXT" "S" "Standard" "J" "C" (list 6565 395.0) 10 0 "4xUTP")
(command "-LAYER" "S" "Cables_UTP" "")
(command "-COLOR" "5")
(command "_.PLINE" (list 6650 750) (list 6650 -20) (list 6510.0 -20) (list 6510.0 -40) "")
(command "-LAYER" "S" "Cables_UTP" "")
(command "-COLOR" "5")
(command "-TEXT" "S" "Standard" "J" "C" (list 6665 365.0) 10 0 "2xUTP")
(command "-LAYER" "S" "Cables_UTP" "")
(command "-COLOR" "5")
(command "_.PLINE" (list 6750 750) (list 6750 -140) (list 6510.0 -140) (list 6510.0 -160) "")
(command "-LAYER" "S" "Cables_UTP" "")
(command "-COLOR" "5")
(command "-TEXT" "S" "Standard" "J" "C" (list 6765 305.0) 10 0 "1xUTP")
(command "-LAYER" "S" "Cables_UTP" "")
(command "-COLOR" "5")
(command "_.PLINE" (list 6850 750) (list 6850 -80) (list 6510.0 -80) (list 6510.0 -100) "")
(command "-LAYER" "S" "Cables_UTP" "")
(command "-COLOR" "5")
(command "-TEXT" "S" "Standard" "J" "C" (list 6865 335.0) 10 0 "10xUTP")
(command "-LAYER" "S" "Cables_UTP" "")
(command "-COLOR" "5")
(command "_.PLINE" (list 6450 950) (list 6450 100) (list 6510.0 100) (list 6510.0 80) "")
(command "-LAYER" "S" "Cables_UTP" "")
(command "-COLOR" "5")
(command "-TEXT" "S" "Standard" "J" "C" (list 6465 525.0) 10 0 "4xUTP")
(command "-LAYER" "S" "Cables_UTP" "")
(command "-COLOR" "5")
(command "_.PLINE" (list 6550 950) (list 6550 40) (list 6510.0 40) (list 6510.0 20) "")
(command "-LAYER" "S" "Cables_UTP" "")
(command "-COLOR" "5")
(command "-TEXT" "S" "Standard" "J" "C" (list 6565 495.0) 10 0 "4xUTP")
(command "-LAYER" "S" "Cables_UTP" "")
(command "-COLOR" "5")
(command "_.PLINE" (list 6650 950) (list 6650 -20) (list 6510.0 -20) (list 6510.0 -40) "")
(command "-LAYER" "S" "Cables_UTP" "")
(command "-COLOR" "5")
(command "-TEXT" "S" "Standard" "J" "C" (list 6665 465.0) 10 0 "2xUTP")
(command "-LAYER" "S" "Cables_UTP" "")
(command "-COLOR" "5")
(command "_.PLINE" (list 6750 950) (list 6750 -140) (list 6510.0 -140) (list 6510.0 -160) "")
(command "-LAYER" "S" "Cables_UTP" "")
(command "-COLOR" "5")
(command "-TEXT" "S" "Standard" "J" "C" (list 6765 405.0) 10 0 "1xUTP")
(command "-LAYER" "S" "Cables_UTP" "")
(command "-COLOR" "5")
(command "_.PLINE" (list 6850 950) (list 6850 -80) (list 6510.0 -80) (list 6510.0 -100) "")
(command "-LAYER" "S" "Cables_UTP" "")
(command "-COLOR" "5")
(command "-TEXT" "S" "Standard" "J" "C" (list 6865 435.0) 10 0 "10xUTP")
(command "-LAYER" "S" "Cables_UTP" "")
(command "-COLOR" "5")
(command "_.PLINE" (list 6450 1150) (list 6450 100) (list 6510.0 100) (list 6510.0 80) "")
(command "-LAYER" "S" "Cables_UTP" "")
(command "-COLOR" "5")
(command "-TEXT" "S" "Standard" "J" "C" (list 6465 625.0) 10 0 "4xUTP")
(command "-LAYER" "S" "Cables_UTP" "")
(command "-COLOR" "5")
(command "_.PLINE" (list 6550 1150) (list 6550 40) (list 6510.0 40) (list 6510.0 20) "")
(command "-LAYER" "S" "Cables_UTP" "")
(command "-COLOR" "5")
(command "-TEXT" "S" "Standard" "J" "C" (list 6565 595.0) 10 0 "4xUTP")
(command "-LAYER" "S" "Cables_UTP" "")
(command "-COLOR" "5")
(command "_.PLINE" (list 6650 1150) (list 6650 -20) (list 6510.0 -20) (list 6510.0 -40) "")
(command "-LAYER" "S" "Cables_UTP" "")
(command "-COLOR" "5")
(command "-TEXT" "S" "Standard" "J" "C" (list 6665 565.0) 10 0 "2xUTP")
(command "-LAYER" "S" "Cables_UTP" "")
(command "-COLOR" "5")
(command "_.PLINE" (list 6750 1150) (list 6750 -140) (list 6510.0 -140) (list 6510.0 -160) "")
(command "-LAYER" "S" "Cables_UTP" "")
(command "-COLOR" "5")
(command "-TEXT" "S" "Standard" "J" "C" (list 6765 505.0) 10 0 "1xUTP")
(command "-LAYER" "S" "Cables_UTP" "")
(command "-COLOR" "5")
(command "_.PLINE" (list 6850 1150) (list 6850 -80) (list 6510.0 -80) (list 6510.0 -100) "")
(command "-LAYER" "S" "Cables_UTP" "")
(command "-COLOR" "5")
(command "-TEXT" "S" "Standard" "J" "C" (list 6865 535.0) 10 0 "10xUTP")
(command "-LAYER" "S" "Cables_UTP" "")
(command "-COLOR" "5")
(command "_.PLINE" (list 6450 1350) (list 6450 100) (list 6510.0 100) (list 6510.0 80) "")
(command "-LAYER" "S" "Cables_UTP" "")
(command "-COLOR" "5")
(command "-TEXT" "S" "Standard" "J" "C" (list 6465 725.0) 10 0 "4xUTP")
(command "-LAYER" "S" "Cables_UTP" "")
(command "-COLOR" "5")
(command "_.PLINE" (list 6550 1350) (list 6550 40) (list 6510.0 40) (list 6510.0 20) "")
(command "-LAYER" "S" "Cables_UTP" "")
(command "-COLOR" "5")
(command "-TEXT" "S" "Standard" "J" "C" (list 6565 695.0) 10 0 "4xUTP")
(command "-LAYER" "S" "Cables_UTP" "")
(command "-COLOR" "5")
(command "_.PLINE" (list 6650 1350) (list 6650 -20) (list 6510.0 -20) (list 6510.0 -40) "")
(command "-LAYER" "S" "Cables_UTP" "")
(command "-COLOR" "5")
(command "-TEXT" "S" "Standard" "J" "C" (list 6665 665.0) 10 0 "2xUTP")
(command "-LAYER" "S" "Cables_UTP" "")
(command "-COLOR" "5")
(command "_.PLINE" (list 6750 1350) (list 6750 -140) (list 6510.0 -140) (list 6510.0 -160) "")
(command "-LAYER" "S" "Cables_UTP" "")
(command "-COLOR" "5")
(command "-TEXT" "S" "Standard" "J" "C" (list 6765 605.0) 10 0 "1xUTP")
(command "-LAYER" "S" "Cables_UTP" "")
(command "-COLOR" "5")
(command "_.PLINE" (list 6850 1350) (list 6850 -80) (list 6510.0 -80) (list 6510.0 -100) "")
(command "-LAYER" "S" "Cables_UTP" "")
(command "-COLOR" "5")
(command "-TEXT" "S" "Standard" "J" "C" (list 6865 635.0) 10 0 "10xUTP")
(command "-LAYER" "S" "Cables_UTP" "")
(command "-COLOR" "5")
(command "_.PLINE" (list 6450 1550) (list 6450 100) (list 6510.0 100) (list 6510.0 80) "")
(command "-LAYER" "S" "Cables_UTP" "")
(command "-COLOR" "5")
(command "-TEXT" "S" "Standard" "J" "C" (list 6465 825.0) 10 0 "2xUTP")
(command "-LAYER" "S" "Cables_UTP" "")
(command "-COLOR" "5")
(command "_.PLINE" (list 6550 1550) (list 6550 40) (list 6510.0 40) (list 6510.0 20) "")
(command "-LAYER" "S" "Cables_UTP" "")
(command "-COLOR" "5")
(command "-TEXT" "S" "Standard" "J" "C" (list 6565 795.0) 10 0 "2xUTP")
(command "-LAYER" "S" "Cables_UTP" "")
(command "-COLOR" "5")
(command "_.PLINE" (list 6650 1550) (list 6650 -20) (list 6510.0 -20) (list 6510.0 -40) "")
(command "-LAYER" "S" "Cables_UTP" "")
(command "-COLOR" "5")
(command "-TEXT" "S" "Standard" "J" "C" (list 6665 765.0) 10 0 "1xUTP")
(command "-LAYER" "S" "Cables_UTP" "")
(command "-COLOR" "5")
(command "_.PLINE" (list 6750 1550) (list 6750 -140) (list 6510.0 -140) (list 6510.0 -160) "")
(command "-LAYER" "S" "Cables_UTP" "")
(command "-COLOR" "5")
(command "-TEXT" "S" "Standard" "J" "C" (list 6765 705.0) 10 0 "1xUTP")
(command "-LAYER" "S" "Cables_UTP" "")
(command "-COLOR" "5")
(command "_.PLINE" (list 6850 1550) (list 6850 -80) (list 6510.0 -80) (list 6510.0 -100) "")
(command "-LAYER" "S" "Cables_UTP" "")
(command "-COLOR" "5")
(command "-TEXT" "S" "Standard" "J" "C" (list 6865 735.0) 10 0 "6xUTP")
(command "-LAYER" "S" "Cables_UTP" "")
(command "-COLOR" "5")
(command "_.PLINE" (list 7500 150) (list 7500 100) (list 7560.0 100) (list 7560.0 80) "")
(command "-LAYER" "S" "Cables_UTP" "")
(command "-COLOR" "5")
(command "-TEXT" "S" "Standard" "J" "C" (list 7515 125.0) 10 0 "2xUTP")
(command "-LAYER" "S" "Cables_UTP" "")
(command "-COLOR" "5")
(command "_.PLINE" (list 7600 150) (list 7600 40) (list 7560.0 40) (list 7560.0 20) "")
(command "-LAYER" "S" "Cables_UTP" "")
(command "-COLOR" "5")
(command "-TEXT" "S" "Standard" "J" "C" (list 7615 95.0) 10 0 "3xUTP")
(command "-LAYER" "S" "Cables_UTP" "")
(command "-COLOR" "5")
(command "_.PLINE" (list 7700 150) (list 7700 -20) (list 7560.0 -20) (list 7560.0 -40) "")
(command "-LAYER" "S" "Cables_UTP" "")
(command "-COLOR" "5")
(command "-TEXT" "S" "Standard" "J" "C" (list 7715 65.0) 10 0 "2xUTP")
(command "-LAYER" "S" "Cables_UTP" "")
(command "-COLOR" "5")
(command "_.PLINE" (list 7800 150) (list 7800 -140) (list 7560.0 -140) (list 7560.0 -160) "")
(command "-LAYER" "S" "Cables_UTP" "")
(command "-COLOR" "5")
(command "-TEXT" "S" "Standard" "J" "C" (list 7815 5.0) 10 0 "1xUTP")
(command "-LAYER" "S" "Cables_UTP" "")
(command "-COLOR" "5")
(command "_.PLINE" (list 7900 150) (list 7900 -80) (list 7560.0 -80) (list 7560.0 -100) "")
(command "-LAYER" "S" "Cables_UTP" "")
(command "-COLOR" "5")
(command "-TEXT" "S" "Standard" "J" "C" (list 7915 35.0) 10 0 "7xUTP")
(command "-LAYER" "S" "Cables_UTP" "")
(command "-COLOR" "5")
(command "_.PLINE" (list 7500 350) (list 7500 100) (list 7560.0 100) (list 7560.0 80) "")
(command "-LAYER" "S" "Cables_UTP" "")
(command "-COLOR" "5")
(command "-TEXT" "S" "Standard" "J" "C" (list 7515 225.0) 10 0 "5xUTP")
(command "-LAYER" "S" "Cables_UTP" "")
(command "-COLOR" "5")
(command "_.PLINE" (list 7600 350) (list 7600 40) (list 7560.0 40) (list 7560.0 20) "")
(command "-LAYER" "S" "Cables_UTP" "")
(command "-COLOR" "5")
(command "-TEXT" "S" "Standard" "J" "C" (list 7615 195.0) 10 0 "6xUTP")
(command "-LAYER" "S" "Cables_UTP" "")
(command "-COLOR" "5")
(command "_.PLINE" (list 7700 350) (list 7700 -20) (list 7560.0 -20) (list 7560.0 -40) "")
(command "-LAYER" "S" "Cables_UTP" "")
(command "-COLOR" "5")
(command "-TEXT" "S" "Standard" "J" "C" (list 7715 165.0) 10 0 "4xUTP")
(command "-LAYER" "S" "Cables_UTP" "")
(command "-COLOR" "5")
(command "_.PLINE" (list 7800 350) (list 7800 -140) (list 7560.0 -140) (list 7560.0 -160) "")
(command "-LAYER" "S" "Cables_UTP" "")
(command "-COLOR" "5")
(command "-TEXT" "S" "Standard" "J" "C" (list 7815 105.0) 10 0 "2xUTP")
(command "-LAYER" "S" "Cables_UTP" "")
(command "-COLOR" "5")
(command "_.PLINE" (list 7900 350) (list 7900 -80) (list 7560.0 -80) (list 7560.0 -100) "")
(command "-LAYER" "S" "Cables_UTP" "")
(command "-COLOR" "5")
(command "-TEXT" "S" "Standard" "J" "C" (list 7915 135.0) 10 0 "14xUTP")
(command "-LAYER" "S" "Cables_UTP" "")
(command "-COLOR" "5")
(command "_.PLINE" (list 7500 550) (list 7500 100) (list 7560.0 100) (list 7560.0 80) "")
(command "-LAYER" "S" "Cables_UTP" "")
(command "-COLOR" "5")
(command "-TEXT" "S" "Standard" "J" "C" (list 7515 325.0) 10 0 "4xUTP")
(command "-LAYER" "S" "Cables_UTP" "")
(command "-COLOR" "5")
(command "_.PLINE" (list 7600 550) (list 7600 40) (list 7560.0 40) (list 7560.0 20) "")
(command "-LAYER" "S" "Cables_UTP" "")
(command "-COLOR" "5")
(command "-TEXT" "S" "Standard" "J" "C" (list 7615 295.0) 10 0 "4xUTP")
(command "-LAYER" "S" "Cables_UTP" "")
(command "-COLOR" "5")
(command "_.PLINE" (list 7700 550) (list 7700 -20) (list 7560.0 -20) (list 7560.0 -40) "")
(command "-LAYER" "S" "Cables_UTP" "")
(command "-COLOR" "5")
(command "-TEXT" "S" "Standard" "J" "C" (list 7715 265.0) 10 0 "2xUTP")
(command "-LAYER" "S" "Cables_UTP" "")
(command "-COLOR" "5")
(command "_.PLINE" (list 7800 550) (list 7800 -140) (list 7560.0 -140) (list 7560.0 -160) "")
(command "-LAYER" "S" "Cables_UTP" "")
(command "-COLOR" "5")
(command "-TEXT" "S" "Standard" "J" "C" (list 7815 205.0) 10 0 "1xUTP")
(command "-LAYER" "S" "Cables_UTP" "")
(command "-COLOR" "5")
(command "_.PLINE" (list 7900 550) (list 7900 -80) (list 7560.0 -80) (list 7560.0 -100) "")
(command "-LAYER" "S" "Cables_UTP" "")
(command "-COLOR" "5")
(command "-TEXT" "S" "Standard" "J" "C" (list 7915 235.0) 10 0 "10xUTP")
(command "-LAYER" "S" "Cables_UTP" "")
(command "-COLOR" "5")
(command "_.PLINE" (list 7500 750) (list 7500 100) (list 7560.0 100) (list 7560.0 80) "")
(command "-LAYER" "S" "Cables_UTP" "")
(command "-COLOR" "5")
(command "-TEXT" "S" "Standard" "J" "C" (list 7515 425.0) 10 0 "4xUTP")
(command "-LAYER" "S" "Cables_UTP" "")
(command "-COLOR" "5")
(command "_.PLINE" (list 7600 750) (list 7600 40) (list 7560.0 40) (list 7560.0 20) "")
(command "-LAYER" "S" "Cables_UTP" "")
(command "-COLOR" "5")
(command "-TEXT" "S" "Standard" "J" "C" (list 7615 395.0) 10 0 "4xUTP")
(command "-LAYER" "S" "Cables_UTP" "")
(command "-COLOR" "5")
(command "_.PLINE" (list 7700 750) (list 7700 -20) (list 7560.0 -20) (list 7560.0 -40) "")
(command "-LAYER" "S" "Cables_UTP" "")
(command "-COLOR" "5")
(command "-TEXT" "S" "Standard" "J" "C" (list 7715 365.0) 10 0 "2xUTP")
(command "-LAYER" "S" "Cables_UTP" "")
(command "-COLOR" "5")
(command "_.PLINE" (list 7800 750) (list 7800 -140) (list 7560.0 -140) (list 7560.0 -160) "")
(command "-LAYER" "S" "Cables_UTP" "")
(command "-COLOR" "5")
(command "-TEXT" "S" "Standard" "J" "C" (list 7815 305.0) 10 0 "1xUTP")
(command "-LAYER" "S" "Cables_UTP" "")
(command "-COLOR" "5")
(command "_.PLINE" (list 7900 750) (list 7900 -80) (list 7560.0 -80) (list 7560.0 -100) "")
(command "-LAYER" "S" "Cables_UTP" "")
(command "-COLOR" "5")
(command "-TEXT" "S" "Standard" "J" "C" (list 7915 335.0) 10 0 "10xUTP")
(command "-LAYER" "S" "Cables_UTP" "")
(command "-COLOR" "5")
(command "_.PLINE" (list 7500 950) (list 7500 100) (list 7560.0 100) (list 7560.0 80) "")
(command "-LAYER" "S" "Cables_UTP" "")
(command "-COLOR" "5")
(command "-TEXT" "S" "Standard" "J" "C" (list 7515 525.0) 10 0 "4xUTP")
(command "-LAYER" "S" "Cables_UTP" "")
(command "-COLOR" "5")
(command "_.PLINE" (list 7600 950) (list 7600 40) (list 7560.0 40) (list 7560.0 20) "")
(command "-LAYER" "S" "Cables_UTP" "")
(command "-COLOR" "5")
(command "-TEXT" "S" "Standard" "J" "C" (list 7615 495.0) 10 0 "4xUTP")
(command "-LAYER" "S" "Cables_UTP" "")
(command "-COLOR" "5")
(command "_.PLINE" (list 7700 950) (list 7700 -20) (list 7560.0 -20) (list 7560.0 -40) "")
(command "-LAYER" "S" "Cables_UTP" "")
(command "-COLOR" "5")
(command "-TEXT" "S" "Standard" "J" "C" (list 7715 465.0) 10 0 "2xUTP")
(command "-LAYER" "S" "Cables_UTP" "")
(command "-COLOR" "5")
(command "_.PLINE" (list 7800 950) (list 7800 -140) (list 7560.0 -140) (list 7560.0 -160) "")
(command "-LAYER" "S" "Cables_UTP" "")
(command "-COLOR" "5")
(command "-TEXT" "S" "Standard" "J" "C" (list 7815 405.0) 10 0 "1xUTP")
(command "-LAYER" "S" "Cables_UTP" "")
(command "-COLOR" "5")
(command "_.PLINE" (list 7900 950) (list 7900 -80) (list 7560.0 -80) (list 7560.0 -100) "")
(command "-LAYER" "S" "Cables_UTP" "")
(command "-COLOR" "5")
(command "-TEXT" "S" "Standard" "J" "C" (list 7915 435.0) 10 0 "10xUTP")
(command "-LAYER" "S" "Cables_UTP" "")
(command "-COLOR" "5")
(command "_.PLINE" (list 7500 1150) (list 7500 100) (list 7560.0 100) (list 7560.0 80) "")
(command "-LAYER" "S" "Cables_UTP" "")
(command "-COLOR" "5")
(command "-TEXT" "S" "Standard" "J" "C" (list 7515 625.0) 10 0 "4xUTP")
(command "-LAYER" "S" "Cables_UTP" "")
(command "-COLOR" "5")
(command "_.PLINE" (list 7600 1150) (list 7600 40) (list 7560.0 40) (list 7560.0 20) "")
(command "-LAYER" "S" "Cables_UTP" "")
(command "-COLOR" "5")
(command "-TEXT" "S" "Standard" "J" "C" (list 7615 595.0) 10 0 "4xUTP")
(command "-LAYER" "S" "Cables_UTP" "")
(command "-COLOR" "5")
(command "_.PLINE" (list 7700 1150) (list 7700 -20) (list 7560.0 -20) (list 7560.0 -40) "")
(command "-LAYER" "S" "Cables_UTP" "")
(command "-COLOR" "5")
(command "-TEXT" "S" "Standard" "J" "C" (list 7715 565.0) 10 0 "2xUTP")
(command "-LAYER" "S" "Cables_UTP" "")
(command "-COLOR" "5")
(command "_.PLINE" (list 7800 1150) (list 7800 -140) (list 7560.0 -140) (list 7560.0 -160) "")
(command "-LAYER" "S" "Cables_UTP" "")
(command "-COLOR" "5")
(command "-TEXT" "S" "Standard" "J" "C" (list 7815 505.0) 10 0 "1xUTP")
(command "-LAYER" "S" "Cables_UTP" "")
(command "-COLOR" "5")
(command "_.PLINE" (list 7900 1150) (list 7900 -80) (list 7560.0 -80) (list 7560.0 -100) "")
(command "-LAYER" "S" "Cables_UTP" "")
(command "-COLOR" "5")
(command "-TEXT" "S" "Standard" "J" "C" (list 7915 535.0) 10 0 "10xUTP")
(command "-LAYER" "S" "Cables_UTP" "")
(command "-COLOR" "5")
(command "_.PLINE" (list 7500 1350) (list 7500 100) (list 7560.0 100) (list 7560.0 80) "")
(command "-LAYER" "S" "Cables_UTP" "")
(command "-COLOR" "5")
(command "-TEXT" "S" "Standard" "J" "C" (list 7515 725.0) 10 0 "4xUTP")
(command "-LAYER" "S" "Cables_UTP" "")
(command "-COLOR" "5")
(command "_.PLINE" (list 7600 1350) (list 7600 40) (list 7560.0 40) (list 7560.0 20) "")
(command "-LAYER" "S" "Cables_UTP" "")
(command "-COLOR" "5")
(command "-TEXT" "S" "Standard" "J" "C" (list 7615 695.0) 10 0 "4xUTP")
(command "-LAYER" "S" "Cables_UTP" "")
(command "-COLOR" "5")
(command "_.PLINE" (list 7700 1350) (list 7700 -20) (list 7560.0 -20) (list 7560.0 -40) "")
(command "-LAYER" "S" "Cables_UTP" "")
(command "-COLOR" "5")
(command "-TEXT" "S" "Standard" "J" "C" (list 7715 665.0) 10 0 "2xUTP")
(command "-LAYER" "S" "Cables_UTP" "")
(command "-COLOR" "5")
(command "_.PLINE" (list 7800 1350) (list 7800 -140) (list 7560.0 -140) (list 7560.0 -160) "")
(command "-LAYER" "S" "Cables_UTP" "")
(command "-COLOR" "5")
(command "-TEXT" "S" "Standard" "J" "C" (list 7815 605.0) 10 0 "1xUTP")
(command "-LAYER" "S" "Cables_UTP" "")
(command "-COLOR" "5")
(command "_.PLINE" (list 7900 1350) (list 7900 -80) (list 7560.0 -80) (list 7560.0 -100) "")
(command "-LAYER" "S" "Cables_UTP" "")
(command "-COLOR" "5")
(command "-TEXT" "S" "Standard" "J" "C" (list 7915 635.0) 10 0 "10xUTP")
(command "-LAYER" "S" "Cables_UTP" "")
(command "-COLOR" "5")
(command "_.PLINE" (list 7500 1550) (list 7500 100) (list 7560.0 100) (list 7560.0 80) "")
(command "-LAYER" "S" "Cables_UTP" "")
(command "-COLOR" "5")
(command "-TEXT" "S" "Standard" "J" "C" (list 7515 825.0) 10 0 "2xUTP")
(command "-LAYER" "S" "Cables_UTP" "")
(command "-COLOR" "5")
(command "_.PLINE" (list 7600 1550) (list 7600 40) (list 7560.0 40) (list 7560.0 20) "")
(command "-LAYER" "S" "Cables_UTP" "")
(command "-COLOR" "5")
(command "-TEXT" "S" "Standard" "J" "C" (list 7615 795.0) 10 0 "2xUTP")
(command "-LAYER" "S" "Cables_UTP" "")
(command "-COLOR" "5")
(command "_.PLINE" (list 7700 1550) (list 7700 -20) (list 7560.0 -20) (list 7560.0 -40) "")
(command "-LAYER" "S" "Cables_UTP" "")
(command "-COLOR" "5")
(command "-TEXT" "S" "Standard" "J" "C" (list 7715 765.0) 10 0 "1xUTP")
(command "-LAYER" "S" "Cables_UTP" "")
(command "-COLOR" "5")
(command "_.PLINE" (list 7800 1550) (list 7800 -140) (list 7560.0 -140) (list 7560.0 -160) "")
(command "-LAYER" "S" "Cables_UTP" "")
(command "-COLOR" "5")
(command "-TEXT" "S" "Standard" "J" "C" (list 7815 705.0) 10 0 "1xUTP")
(command "-LAYER" "S" "Cables_UTP" "")
(command "-COLOR" "5")
(command "_.PLINE" (list 7900 1550) (list 7900 -80) (list 7560.0 -80) (list 7560.0 -100) "")
(command "-LAYER" "S" "Cables_UTP" "")
(command "-COLOR" "5")
(command "-TEXT" "S" "Standard" "J" "C" (list 7915 735.0) 10 0 "6xUTP")
(command "-LAYER" "S" "Cables_UTP" "")
(command "-COLOR" "5")
(command "_.PLINE" (list 8550 150) (list 8550 100) (list 8610.0 100) (list 8610.0 80) "")
(command "-LAYER" "S" "Cables_UTP" "")
(command "-COLOR" "5")
(command "-TEXT" "S" "Standard" "J" "C" (list 8565 125.0) 10 0 "1xUTP")
(command "-LAYER" "S" "Cables_UTP" "")
(command "-COLOR" "5")
(command "_.PLINE" (list 8650 150) (list 8650 40) (list 8610.0 40) (list 8610.0 20) "")
(command "-LAYER" "S" "Cables_UTP" "")
(command "-COLOR" "5")
(command "-TEXT" "S" "Standard" "J" "C" (list 8665 95.0) 10 0 "2xUTP")
(command "-LAYER" "S" "Cables_UTP" "")
(command "-COLOR" "5")
(command "_.PLINE" (list 8750 150) (list 8750 -20) (list 8610.0 -20) (list 8610.0 -40) "")
(command "-LAYER" "S" "Cables_UTP" "")
(command "-COLOR" "5")
(command "-TEXT" "S" "Standard" "J" "C" (list 8765 65.0) 10 0 "1xUTP")
(command "-LAYER" "S" "Cables_UTP" "")
(command "-COLOR" "5")
(command "_.PLINE" (list 8850 150) (list 8850 -140) (list 8610.0 -140) (list 8610.0 -160) "")
(command "-LAYER" "S" "Cables_UTP" "")
(command "-COLOR" "5")
(command "-TEXT" "S" "Standard" "J" "C" (list 8865 5.0) 10 0 "1xUTP")
(command "-LAYER" "S" "Cables_UTP" "")
(command "-COLOR" "5")
(command "_.PLINE" (list 8950 150) (list 8950 -80) (list 8610.0 -80) (list 8610.0 -100) "")
(command "-LAYER" "S" "Cables_UTP" "")
(command "-COLOR" "5")
(command "-TEXT" "S" "Standard" "J" "C" (list 8965 35.0) 10 0 "5xUTP")
(command "-LAYER" "S" "Cables_UTP" "")
(command "-COLOR" "5")
(command "_.PLINE" (list 8550 350) (list 8550 100) (list 8610.0 100) (list 8610.0 80) "")
(command "-LAYER" "S" "Cables_UTP" "")
(command "-COLOR" "5")
(command "-TEXT" "S" "Standard" "J" "C" (list 8565 225.0) 10 0 "4xUTP")
(command "-LAYER" "S" "Cables_UTP" "")
(command "-COLOR" "5")
(command "_.PLINE" (list 8650 350) (list 8650 40) (list 8610.0 40) (list 8610.0 20) "")
(command "-LAYER" "S" "Cables_UTP" "")
(command "-COLOR" "5")
(command "-TEXT" "S" "Standard" "J" "C" (list 8665 195.0) 10 0 "5xUTP")
(command "-LAYER" "S" "Cables_UTP" "")
(command "-COLOR" "5")
(command "_.PLINE" (list 8750 350) (list 8750 -20) (list 8610.0 -20) (list 8610.0 -40) "")
(command "-LAYER" "S" "Cables_UTP" "")
(command "-COLOR" "5")
(command "-TEXT" "S" "Standard" "J" "C" (list 8765 165.0) 10 0 "3xUTP")
(command "-LAYER" "S" "Cables_UTP" "")
(command "-COLOR" "5")
(command "_.PLINE" (list 8850 350) (list 8850 -140) (list 8610.0 -140) (list 8610.0 -160) "")
(command "-LAYER" "S" "Cables_UTP" "")
(command "-COLOR" "5")
(command "-TEXT" "S" "Standard" "J" "C" (list 8865 105.0) 10 0 "2xUTP")
(command "-LAYER" "S" "Cables_UTP" "")
(command "-COLOR" "5")
(command "_.PLINE" (list 8950 350) (list 8950 -80) (list 8610.0 -80) (list 8610.0 -100) "")
(command "-LAYER" "S" "Cables_UTP" "")
(command "-COLOR" "5")
(command "-TEXT" "S" "Standard" "J" "C" (list 8965 135.0) 10 0 "12xUTP")
(command "-LAYER" "S" "Cables_UTP" "")
(command "-COLOR" "5")
(command "_.PLINE" (list 8550 550) (list 8550 100) (list 8610.0 100) (list 8610.0 80) "")
(command "-LAYER" "S" "Cables_UTP" "")
(command "-COLOR" "5")
(command "-TEXT" "S" "Standard" "J" "C" (list 8565 325.0) 10 0 "4xUTP")
(command "-LAYER" "S" "Cables_UTP" "")
(command "-COLOR" "5")
(command "_.PLINE" (list 8650 550) (list 8650 40) (list 8610.0 40) (list 8610.0 20) "")
(command "-LAYER" "S" "Cables_UTP" "")
(command "-COLOR" "5")
(command "-TEXT" "S" "Standard" "J" "C" (list 8665 295.0) 10 0 "4xUTP")
(command "-LAYER" "S" "Cables_UTP" "")
(command "-COLOR" "5")
(command "_.PLINE" (list 8750 550) (list 8750 -20) (list 8610.0 -20) (list 8610.0 -40) "")
(command "-LAYER" "S" "Cables_UTP" "")
(command "-COLOR" "5")
(command "-TEXT" "S" "Standard" "J" "C" (list 8765 265.0) 10 0 "2xUTP")
(command "-LAYER" "S" "Cables_UTP" "")
(command "-COLOR" "5")
(command "_.PLINE" (list 8850 550) (list 8850 -140) (list 8610.0 -140) (list 8610.0 -160) "")
(command "-LAYER" "S" "Cables_UTP" "")
(command "-COLOR" "5")
(command "-TEXT" "S" "Standard" "J" "C" (list 8865 205.0) 10 0 "1xUTP")
(command "-LAYER" "S" "Cables_UTP" "")
(command "-COLOR" "5")
(command "_.PLINE" (list 8950 550) (list 8950 -80) (list 8610.0 -80) (list 8610.0 -100) "")
(command "-LAYER" "S" "Cables_UTP" "")
(command "-COLOR" "5")
(command "-TEXT" "S" "Standard" "J" "C" (list 8965 235.0) 10 0 "10xUTP")
(command "-LAYER" "S" "Cables_UTP" "")
(command "-COLOR" "5")
(command "_.PLINE" (list 8550 750) (list 8550 100) (list 8610.0 100) (list 8610.0 80) "")
(command "-LAYER" "S" "Cables_UTP" "")
(command "-COLOR" "5")
(command "-TEXT" "S" "Standard" "J" "C" (list 8565 425.0) 10 0 "4xUTP")
(command "-LAYER" "S" "Cables_UTP" "")
(command "-COLOR" "5")
(command "_.PLINE" (list 8650 750) (list 8650 40) (list 8610.0 40) (list 8610.0 20) "")
(command "-LAYER" "S" "Cables_UTP" "")
(command "-COLOR" "5")
(command "-TEXT" "S" "Standard" "J" "C" (list 8665 395.0) 10 0 "4xUTP")
(command "-LAYER" "S" "Cables_UTP" "")
(command "-COLOR" "5")
(command "_.PLINE" (list 8750 750) (list 8750 -20) (list 8610.0 -20) (list 8610.0 -40) "")
(command "-LAYER" "S" "Cables_UTP" "")
(command "-COLOR" "5")
(command "-TEXT" "S" "Standard" "J" "C" (list 8765 365.0) 10 0 "2xUTP")
(command "-LAYER" "S" "Cables_UTP" "")
(command "-COLOR" "5")
(command "_.PLINE" (list 8850 750) (list 8850 -140) (list 8610.0 -140) (list 8610.0 -160) "")
(command "-LAYER" "S" "Cables_UTP" "")
(command "-COLOR" "5")
(command "-TEXT" "S" "Standard" "J" "C" (list 8865 305.0) 10 0 "1xUTP")
(command "-LAYER" "S" "Cables_UTP" "")
(command "-COLOR" "5")
(command "_.PLINE" (list 8950 750) (list 8950 -80) (list 8610.0 -80) (list 8610.0 -100) "")
(command "-LAYER" "S" "Cables_UTP" "")
(command "-COLOR" "5")
(command "-TEXT" "S" "Standard" "J" "C" (list 8965 335.0) 10 0 "10xUTP")
(command "-LAYER" "S" "Cables_UTP" "")
(command "-COLOR" "5")
(command "_.PLINE" (list 8550 950) (list 8550 100) (list 8610.0 100) (list 8610.0 80) "")
(command "-LAYER" "S" "Cables_UTP" "")
(command "-COLOR" "5")
(command "-TEXT" "S" "Standard" "J" "C" (list 8565 525.0) 10 0 "4xUTP")
(command "-LAYER" "S" "Cables_UTP" "")
(command "-COLOR" "5")
(command "_.PLINE" (list 8650 950) (list 8650 40) (list 8610.0 40) (list 8610.0 20) "")
(command "-LAYER" "S" "Cables_UTP" "")
(command "-COLOR" "5")
(command "-TEXT" "S" "Standard" "J" "C" (list 8665 495.0) 10 0 "4xUTP")
(command "-LAYER" "S" "Cables_UTP" "")
(command "-COLOR" "5")
(command "_.PLINE" (list 8750 950) (list 8750 -20) (list 8610.0 -20) (list 8610.0 -40) "")
(command "-LAYER" "S" "Cables_UTP" "")
(command "-COLOR" "5")
(command "-TEXT" "S" "Standard" "J" "C" (list 8765 465.0) 10 0 "2xUTP")
(command "-LAYER" "S" "Cables_UTP" "")
(command "-COLOR" "5")
(command "_.PLINE" (list 8850 950) (list 8850 -140) (list 8610.0 -140) (list 8610.0 -160) "")
(command "-LAYER" "S" "Cables_UTP" "")
(command "-COLOR" "5")
(command "-TEXT" "S" "Standard" "J" "C" (list 8865 405.0) 10 0 "1xUTP")
(command "-LAYER" "S" "Cables_UTP" "")
(command "-COLOR" "5")
(command "_.PLINE" (list 8950 950) (list 8950 -80) (list 8610.0 -80) (list 8610.0 -100) "")
(command "-LAYER" "S" "Cables_UTP" "")
(command "-COLOR" "5")
(command "-TEXT" "S" "Standard" "J" "C" (list 8965 435.0) 10 0 "10xUTP")
(command "-LAYER" "S" "Cables_UTP" "")
(command "-COLOR" "5")
(command "_.PLINE" (list 8550 1150) (list 8550 100) (list 8610.0 100) (list 8610.0 80) "")
(command "-LAYER" "S" "Cables_UTP" "")
(command "-COLOR" "5")
(command "-TEXT" "S" "Standard" "J" "C" (list 8565 625.0) 10 0 "4xUTP")
(command "-LAYER" "S" "Cables_UTP" "")
(command "-COLOR" "5")
(command "_.PLINE" (list 8650 1150) (list 8650 40) (list 8610.0 40) (list 8610.0 20) "")
(command "-LAYER" "S" "Cables_UTP" "")
(command "-COLOR" "5")
(command "-TEXT" "S" "Standard" "J" "C" (list 8665 595.0) 10 0 "4xUTP")
(command "-LAYER" "S" "Cables_UTP" "")
(command "-COLOR" "5")
(command "_.PLINE" (list 8750 1150) (list 8750 -20) (list 8610.0 -20) (list 8610.0 -40) "")
(command "-LAYER" "S" "Cables_UTP" "")
(command "-COLOR" "5")
(command "-TEXT" "S" "Standard" "J" "C" (list 8765 565.0) 10 0 "2xUTP")
(command "-LAYER" "S" "Cables_UTP" "")
(command "-COLOR" "5")
(command "_.PLINE" (list 8850 1150) (list 8850 -140) (list 8610.0 -140) (list 8610.0 -160) "")
(command "-LAYER" "S" "Cables_UTP" "")
(command "-COLOR" "5")
(command "-TEXT" "S" "Standard" "J" "C" (list 8865 505.0) 10 0 "1xUTP")
(command "-LAYER" "S" "Cables_UTP" "")
(command "-COLOR" "5")
(command "_.PLINE" (list 8950 1150) (list 8950 -80) (list 8610.0 -80) (list 8610.0 -100) "")
(command "-LAYER" "S" "Cables_UTP" "")
(command "-COLOR" "5")
(command "-TEXT" "S" "Standard" "J" "C" (list 8965 535.0) 10 0 "10xUTP")
(command "-LAYER" "S" "Cables_UTP" "")
(command "-COLOR" "5")
(command "_.PLINE" (list 8550 1350) (list 8550 100) (list 8610.0 100) (list 8610.0 80) "")
(command "-LAYER" "S" "Cables_UTP" "")
(command "-COLOR" "5")
(command "-TEXT" "S" "Standard" "J" "C" (list 8565 725.0) 10 0 "4xUTP")
(command "-LAYER" "S" "Cables_UTP" "")
(command "-COLOR" "5")
(command "_.PLINE" (list 8650 1350) (list 8650 40) (list 8610.0 40) (list 8610.0 20) "")
(command "-LAYER" "S" "Cables_UTP" "")
(command "-COLOR" "5")
(command "-TEXT" "S" "Standard" "J" "C" (list 8665 695.0) 10 0 "4xUTP")
(command "-LAYER" "S" "Cables_UTP" "")
(command "-COLOR" "5")
(command "_.PLINE" (list 8750 1350) (list 8750 -20) (list 8610.0 -20) (list 8610.0 -40) "")
(command "-LAYER" "S" "Cables_UTP" "")
(command "-COLOR" "5")
(command "-TEXT" "S" "Standard" "J" "C" (list 8765 665.0) 10 0 "2xUTP")
(command "-LAYER" "S" "Cables_UTP" "")
(command "-COLOR" "5")
(command "_.PLINE" (list 8850 1350) (list 8850 -140) (list 8610.0 -140) (list 8610.0 -160) "")
(command "-LAYER" "S" "Cables_UTP" "")
(command "-COLOR" "5")
(command "-TEXT" "S" "Standard" "J" "C" (list 8865 605.0) 10 0 "1xUTP")
(command "-LAYER" "S" "Cables_UTP" "")
(command "-COLOR" "5")
(command "_.PLINE" (list 8950 1350) (list 8950 -80) (list 8610.0 -80) (list 8610.0 -100) "")
(command "-LAYER" "S" "Cables_UTP" "")
(command "-COLOR" "5")
(command "-TEXT" "S" "Standard" "J" "C" (list 8965 635.0) 10 0 "10xUTP")
(command "-LAYER" "S" "Cables_UTP" "")
(command "-COLOR" "5")
(command "_.PLINE" (list 8550 1550) (list 8550 100) (list 8610.0 100) (list 8610.0 80) "")
(command "-LAYER" "S" "Cables_UTP" "")
(command "-COLOR" "5")
(command "-TEXT" "S" "Standard" "J" "C" (list 8565 825.0) 10 0 "2xUTP")
(command "-LAYER" "S" "Cables_UTP" "")
(command "-COLOR" "5")
(command "_.PLINE" (list 8650 1550) (list 8650 40) (list 8610.0 40) (list 8610.0 20) "")
(command "-LAYER" "S" "Cables_UTP" "")
(command "-COLOR" "5")
(command "-TEXT" "S" "Standard" "J" "C" (list 8665 795.0) 10 0 "2xUTP")
(command "-LAYER" "S" "Cables_UTP" "")
(command "-COLOR" "5")
(command "_.PLINE" (list 8750 1550) (list 8750 -20) (list 8610.0 -20) (list 8610.0 -40) "")
(command "-LAYER" "S" "Cables_UTP" "")
(command "-COLOR" "5")
(command "-TEXT" "S" "Standard" "J" "C" (list 8765 765.0) 10 0 "1xUTP")
(command "-LAYER" "S" "Cables_UTP" "")
(command "-COLOR" "5")
(command "_.PLINE" (list 8850 1550) (list 8850 -140) (list 8610.0 -140) (list 8610.0 -160) "")
(command "-LAYER" "S" "Cables_UTP" "")
(command "-COLOR" "5")
(command "-TEXT" "S" "Standard" "J" "C" (list 8865 705.0) 10 0 "1xUTP")
(command "-LAYER" "S" "Cables_UTP" "")
(command "-COLOR" "5")
(command "_.PLINE" (list 8950 1550) (list 8950 -80) (list 8610.0 -80) (list 8610.0 -100) "")
(command "-LAYER" "S" "Cables_UTP" "")
(command "-COLOR" "5")
(command "-TEXT" "S" "Standard" "J" "C" (list 8965 735.0) 10 0 "6xUTP")
(command "-LAYER" "S" "Cables_UTP" "")
(command "-COLOR" "5")
(command "_.PLINE" (list 9600 150) (list 9600 40) (list 9660.0 40) (list 9660.0 20) "")
(command "-LAYER" "S" "Cables_UTP" "")
(command "-COLOR" "5")
(command "-TEXT" "S" "Standard" "J" "C" (list 9615 95.0) 10 0 "1xUTP")
(command "-LAYER" "S" "Cables_UTP" "")
(command "-COLOR" "5")
(command "_.PLINE" (list 9700 150) (list 9700 -140) (list 9660.0 -140) (list 9660.0 -160) "")
(command "-LAYER" "S" "Cables_UTP" "")
(command "-COLOR" "5")
(command "-TEXT" "S" "Standard" "J" "C" (list 9715 5.0) 10 0 "1xUTP")
(command "-LAYER" "S" "Cables_UTP" "")
(command "-COLOR" "5")
(command "_.PLINE" (list 9800 150) (list 9800 -80) (list 9660.0 -80) (list 9660.0 -100) "")
(command "-LAYER" "S" "Cables_UTP" "")
(command "-COLOR" "5")
(command "-TEXT" "S" "Standard" "J" "C" (list 9815 35.0) 10 0 "3xUTP")
(command "-LAYER" "S" "Cables_UTP" "")
(command "-COLOR" "5")
(command "_.PLINE" (list 9600 350) (list 9600 100) (list 9660.0 100) (list 9660.0 80) "")
(command "-LAYER" "S" "Cables_UTP" "")
(command "-COLOR" "5")
(command "-TEXT" "S" "Standard" "J" "C" (list 9615 225.0) 10 0 "4xUTP")
(command "-LAYER" "S" "Cables_UTP" "")
(command "-COLOR" "5")
(command "_.PLINE" (list 9700 350) (list 9700 40) (list 9660.0 40) (list 9660.0 20) "")
(command "-LAYER" "S" "Cables_UTP" "")
(command "-COLOR" "5")
(command "-TEXT" "S" "Standard" "J" "C" (list 9715 195.0) 10 0 "5xUTP")
(command "-LAYER" "S" "Cables_UTP" "")
(command "-COLOR" "5")
(command "_.PLINE" (list 9800 350) (list 9800 -20) (list 9660.0 -20) (list 9660.0 -40) "")
(command "-LAYER" "S" "Cables_UTP" "")
(command "-COLOR" "5")
(command "-TEXT" "S" "Standard" "J" "C" (list 9815 165.0) 10 0 "3xUTP")
(command "-LAYER" "S" "Cables_UTP" "")
(command "-COLOR" "5")
(command "_.PLINE" (list 9900 350) (list 9900 -140) (list 9660.0 -140) (list 9660.0 -160) "")
(command "-LAYER" "S" "Cables_UTP" "")
(command "-COLOR" "5")
(command "-TEXT" "S" "Standard" "J" "C" (list 9915 105.0) 10 0 "2xUTP")
(command "-LAYER" "S" "Cables_UTP" "")
(command "-COLOR" "5")
(command "_.PLINE" (list 10000 350) (list 10000 -80) (list 9660.0 -80) (list 9660.0 -100) "")
(command "-LAYER" "S" "Cables_UTP" "")
(command "-COLOR" "5")
(command "-TEXT" "S" "Standard" "J" "C" (list 10015 135.0) 10 0 "12xUTP")
(command "-LAYER" "S" "Cables_UTP" "")
(command "-COLOR" "5")
(command "_.PLINE" (list 9600 550) (list 9600 100) (list 9660.0 100) (list 9660.0 80) "")
(command "-LAYER" "S" "Cables_UTP" "")
(command "-COLOR" "5")
(command "-TEXT" "S" "Standard" "J" "C" (list 9615 325.0) 10 0 "4xUTP")
(command "-LAYER" "S" "Cables_UTP" "")
(command "-COLOR" "5")
(command "_.PLINE" (list 9700 550) (list 9700 40) (list 9660.0 40) (list 9660.0 20) "")
(command "-LAYER" "S" "Cables_UTP" "")
(command "-COLOR" "5")
(command "-TEXT" "S" "Standard" "J" "C" (list 9715 295.0) 10 0 "4xUTP")
(command "-LAYER" "S" "Cables_UTP" "")
(command "-COLOR" "5")
(command "_.PLINE" (list 9800 550) (list 9800 -20) (list 9660.0 -20) (list 9660.0 -40) "")
(command "-LAYER" "S" "Cables_UTP" "")
(command "-COLOR" "5")
(command "-TEXT" "S" "Standard" "J" "C" (list 9815 265.0) 10 0 "2xUTP")
(command "-LAYER" "S" "Cables_UTP" "")
(command "-COLOR" "5")
(command "_.PLINE" (list 9900 550) (list 9900 -140) (list 9660.0 -140) (list 9660.0 -160) "")
(command "-LAYER" "S" "Cables_UTP" "")
(command "-COLOR" "5")
(command "-TEXT" "S" "Standard" "J" "C" (list 9915 205.0) 10 0 "1xUTP")
(command "-LAYER" "S" "Cables_UTP" "")
(command "-COLOR" "5")
(command "_.PLINE" (list 10000 550) (list 10000 -80) (list 9660.0 -80) (list 9660.0 -100) "")
(command "-LAYER" "S" "Cables_UTP" "")
(command "-COLOR" "5")
(command "-TEXT" "S" "Standard" "J" "C" (list 10015 235.0) 10 0 "10xUTP")
(command "-LAYER" "S" "Cables_UTP" "")
(command "-COLOR" "5")
(command "_.PLINE" (list 9600 750) (list 9600 100) (list 9660.0 100) (list 9660.0 80) "")
(command "-LAYER" "S" "Cables_UTP" "")
(command "-COLOR" "5")
(command "-TEXT" "S" "Standard" "J" "C" (list 9615 425.0) 10 0 "4xUTP")
(command "-LAYER" "S" "Cables_UTP" "")
(command "-COLOR" "5")
(command "_.PLINE" (list 9700 750) (list 9700 40) (list 9660.0 40) (list 9660.0 20) "")
(command "-LAYER" "S" "Cables_UTP" "")
(command "-COLOR" "5")
(command "-TEXT" "S" "Standard" "J" "C" (list 9715 395.0) 10 0 "4xUTP")
(command "-LAYER" "S" "Cables_UTP" "")
(command "-COLOR" "5")
(command "_.PLINE" (list 9800 750) (list 9800 -20) (list 9660.0 -20) (list 9660.0 -40) "")
(command "-LAYER" "S" "Cables_UTP" "")
(command "-COLOR" "5")
(command "-TEXT" "S" "Standard" "J" "C" (list 9815 365.0) 10 0 "2xUTP")
(command "-LAYER" "S" "Cables_UTP" "")
(command "-COLOR" "5")
(command "_.PLINE" (list 9900 750) (list 9900 -140) (list 9660.0 -140) (list 9660.0 -160) "")
(command "-LAYER" "S" "Cables_UTP" "")
(command "-COLOR" "5")
(command "-TEXT" "S" "Standard" "J" "C" (list 9915 305.0) 10 0 "1xUTP")
(command "-LAYER" "S" "Cables_UTP" "")
(command "-COLOR" "5")
(command "_.PLINE" (list 10000 750) (list 10000 -80) (list 9660.0 -80) (list 9660.0 -100) "")
(command "-LAYER" "S" "Cables_UTP" "")
(command "-COLOR" "5")
(command "-TEXT" "S" "Standard" "J" "C" (list 10015 335.0) 10 0 "10xUTP")
(command "-LAYER" "S" "Cables_UTP" "")
(command "-COLOR" "5")
(command "_.PLINE" (list 9600 950) (list 9600 100) (list 9660.0 100) (list 9660.0 80) "")
(command "-LAYER" "S" "Cables_UTP" "")
(command "-COLOR" "5")
(command "-TEXT" "S" "Standard" "J" "C" (list 9615 525.0) 10 0 "4xUTP")
(command "-LAYER" "S" "Cables_UTP" "")
(command "-COLOR" "5")
(command "_.PLINE" (list 9700 950) (list 9700 40) (list 9660.0 40) (list 9660.0 20) "")
(command "-LAYER" "S" "Cables_UTP" "")
(command "-COLOR" "5")
(command "-TEXT" "S" "Standard" "J" "C" (list 9715 495.0) 10 0 "4xUTP")
(command "-LAYER" "S" "Cables_UTP" "")
(command "-COLOR" "5")
(command "_.PLINE" (list 9800 950) (list 9800 -20) (list 9660.0 -20) (list 9660.0 -40) "")
(command "-LAYER" "S" "Cables_UTP" "")
(command "-COLOR" "5")
(command "-TEXT" "S" "Standard" "J" "C" (list 9815 465.0) 10 0 "2xUTP")
(command "-LAYER" "S" "Cables_UTP" "")
(command "-COLOR" "5")
(command "_.PLINE" (list 9900 950) (list 9900 -140) (list 9660.0 -140) (list 9660.0 -160) "")
(command "-LAYER" "S" "Cables_UTP" "")
(command "-COLOR" "5")
(command "-TEXT" "S" "Standard" "J" "C" (list 9915 405.0) 10 0 "1xUTP")
(command "-LAYER" "S" "Cables_UTP" "")
(command "-COLOR" "5")
(command "_.PLINE" (list 10000 950) (list 10000 -80) (list 9660.0 -80) (list 9660.0 -100) "")
(command "-LAYER" "S" "Cables_UTP" "")
(command "-COLOR" "5")
(command "-TEXT" "S" "Standard" "J" "C" (list 10015 435.0) 10 0 "10xUTP")
(command "-LAYER" "S" "Cables_UTP" "")
(command "-COLOR" "5")
(command "_.PLINE" (list 9600 1150) (list 9600 100) (list 9660.0 100) (list 9660.0 80) "")
(command "-LAYER" "S" "Cables_UTP" "")
(command "-COLOR" "5")
(command "-TEXT" "S" "Standard" "J" "C" (list 9615 625.0) 10 0 "4xUTP")
(command "-LAYER" "S" "Cables_UTP" "")
(command "-COLOR" "5")
(command "_.PLINE" (list 9700 1150) (list 9700 40) (list 9660.0 40) (list 9660.0 20) "")
(command "-LAYER" "S" "Cables_UTP" "")
(command "-COLOR" "5")
(command "-TEXT" "S" "Standard" "J" "C" (list 9715 595.0) 10 0 "4xUTP")
(command "-LAYER" "S" "Cables_UTP" "")
(command "-COLOR" "5")
(command "_.PLINE" (list 9800 1150) (list 9800 -20) (list 9660.0 -20) (list 9660.0 -40) "")
(command "-LAYER" "S" "Cables_UTP" "")
(command "-COLOR" "5")
(command "-TEXT" "S" "Standard" "J" "C" (list 9815 565.0) 10 0 "2xUTP")
(command "-LAYER" "S" "Cables_UTP" "")
(command "-COLOR" "5")
(command "_.PLINE" (list 9900 1150) (list 9900 -140) (list 9660.0 -140) (list 9660.0 -160) "")
(command "-LAYER" "S" "Cables_UTP" "")
(command "-COLOR" "5")
(command "-TEXT" "S" "Standard" "J" "C" (list 9915 505.0) 10 0 "1xUTP")
(command "-LAYER" "S" "Cables_UTP" "")
(command "-COLOR" "5")
(command "_.PLINE" (list 10000 1150) (list 10000 -80) (list 9660.0 -80) (list 9660.0 -100) "")
(command "-LAYER" "S" "Cables_UTP" "")
(command "-COLOR" "5")
(command "-TEXT" "S" "Standard" "J" "C" (list 10015 535.0) 10 0 "10xUTP")
(command "-LAYER" "S" "Cables_UTP" "")
(command "-COLOR" "5")
(command "_.PLINE" (list 9600 1350) (list 9600 100) (list 9660.0 100) (list 9660.0 80) "")
(command "-LAYER" "S" "Cables_UTP" "")
(command "-COLOR" "5")
(command "-TEXT" "S" "Standard" "J" "C" (list 9615 725.0) 10 0 "4xUTP")
(command "-LAYER" "S" "Cables_UTP" "")
(command "-COLOR" "5")
(command "_.PLINE" (list 9700 1350) (list 9700 40) (list 9660.0 40) (list 9660.0 20) "")
(command "-LAYER" "S" "Cables_UTP" "")
(command "-COLOR" "5")
(command "-TEXT" "S" "Standard" "J" "C" (list 9715 695.0) 10 0 "4xUTP")
(command "-LAYER" "S" "Cables_UTP" "")
(command "-COLOR" "5")
(command "_.PLINE" (list 9800 1350) (list 9800 -20) (list 9660.0 -20) (list 9660.0 -40) "")
(command "-LAYER" "S" "Cables_UTP" "")
(command "-COLOR" "5")
(command "-TEXT" "S" "Standard" "J" "C" (list 9815 665.0) 10 0 "2xUTP")
(command "-LAYER" "S" "Cables_UTP" "")
(command "-COLOR" "5")
(command "_.PLINE" (list 9900 1350) (list 9900 -140) (list 9660.0 -140) (list 9660.0 -160) "")
(command "-LAYER" "S" "Cables_UTP" "")
(command "-COLOR" "5")
(command "-TEXT" "S" "Standard" "J" "C" (list 9915 605.0) 10 0 "1xUTP")
(command "-LAYER" "S" "Cables_UTP" "")
(command "-COLOR" "5")
(command "_.PLINE" (list 10000 1350) (list 10000 -80) (list 9660.0 -80) (list 9660.0 -100) "")
(command "-LAYER" "S" "Cables_UTP" "")
(command "-COLOR" "5")
(command "-TEXT" "S" "Standard" "J" "C" (list 10015 635.0) 10 0 "10xUTP")
(command "-LAYER" "S" "Cables_UTP" "")
(command "-COLOR" "5")
(command "_.PLINE" (list 9600 1550) (list 9600 100) (list 9660.0 100) (list 9660.0 80) "")
(command "-LAYER" "S" "Cables_UTP" "")
(command "-COLOR" "5")
(command "-TEXT" "S" "Standard" "J" "C" (list 9615 825.0) 10 0 "2xUTP")
(command "-LAYER" "S" "Cables_UTP" "")
(command "-COLOR" "5")
(command "_.PLINE" (list 9700 1550) (list 9700 40) (list 9660.0 40) (list 9660.0 20) "")
(command "-LAYER" "S" "Cables_UTP" "")
(command "-COLOR" "5")
(command "-TEXT" "S" "Standard" "J" "C" (list 9715 795.0) 10 0 "2xUTP")
(command "-LAYER" "S" "Cables_UTP" "")
(command "-COLOR" "5")
(command "_.PLINE" (list 9800 1550) (list 9800 -20) (list 9660.0 -20) (list 9660.0 -40) "")
(command "-LAYER" "S" "Cables_UTP" "")
(command "-COLOR" "5")
(command "-TEXT" "S" "Standard" "J" "C" (list 9815 765.0) 10 0 "1xUTP")
(command "-LAYER" "S" "Cables_UTP" "")
(command "-COLOR" "5")
(command "_.PLINE" (list 9900 1550) (list 9900 -140) (list 9660.0 -140) (list 9660.0 -160) "")
(command "-LAYER" "S" "Cables_UTP" "")
(command "-COLOR" "5")
(command "-TEXT" "S" "Standard" "J" "C" (list 9915 705.0) 10 0 "1xUTP")
(command "-LAYER" "S" "Cables_UTP" "")
(command "-COLOR" "5")
(command "_.PLINE" (list 10000 1550) (list 10000 -80) (list 9660.0 -80) (list 9660.0 -100) "")
(command "-LAYER" "S" "Cables_UTP" "")
(command "-COLOR" "5")
(command "-TEXT" "S" "Standard" "J" "C" (list 10015 735.0) 10 0 "6xUTP")
(command "-LAYER" "S" "Cables_UTP" "")
(command "-COLOR" "5")
(command "_.PLINE" (list 10650 150) (list 10650 100) (list 10710.0 100) (list 10710.0 80) "")
(command "-LAYER" "S" "Cables_UTP" "")
(command "-COLOR" "5")
(command "-TEXT" "S" "Standard" "J" "C" (list 10665 125.0) 10 0 "1xUTP")
(command "-LAYER" "S" "Cables_UTP" "")
(command "-COLOR" "5")
(command "_.PLINE" (list 10750 150) (list 10750 40) (list 10710.0 40) (list 10710.0 20) "")
(command "-LAYER" "S" "Cables_UTP" "")
(command "-COLOR" "5")
(command "-TEXT" "S" "Standard" "J" "C" (list 10765 95.0) 10 0 "2xUTP")
(command "-LAYER" "S" "Cables_UTP" "")
(command "-COLOR" "5")
(command "_.PLINE" (list 10850 150) (list 10850 -20) (list 10710.0 -20) (list 10710.0 -40) "")
(command "-LAYER" "S" "Cables_UTP" "")
(command "-COLOR" "5")
(command "-TEXT" "S" "Standard" "J" "C" (list 10865 65.0) 10 0 "1xUTP")
(command "-LAYER" "S" "Cables_UTP" "")
(command "-COLOR" "5")
(command "_.PLINE" (list 10950 150) (list 10950 -140) (list 10710.0 -140) (list 10710.0 -160) "")
(command "-LAYER" "S" "Cables_UTP" "")
(command "-COLOR" "5")
(command "-TEXT" "S" "Standard" "J" "C" (list 10965 5.0) 10 0 "1xUTP")
(command "-LAYER" "S" "Cables_UTP" "")
(command "-COLOR" "5")
(command "_.PLINE" (list 11050 150) (list 11050 -80) (list 10710.0 -80) (list 10710.0 -100) "")
(command "-LAYER" "S" "Cables_UTP" "")
(command "-COLOR" "5")
(command "-TEXT" "S" "Standard" "J" "C" (list 11065 35.0) 10 0 "5xUTP")
(command "-LAYER" "S" "Cables_UTP" "")
(command "-COLOR" "5")
(command "_.PLINE" (list 10650 350) (list 10650 100) (list 10710.0 100) (list 10710.0 80) "")
(command "-LAYER" "S" "Cables_UTP" "")
(command "-COLOR" "5")
(command "-TEXT" "S" "Standard" "J" "C" (list 10665 225.0) 10 0 "4xUTP")
(command "-LAYER" "S" "Cables_UTP" "")
(command "-COLOR" "5")
(command "_.PLINE" (list 10750 350) (list 10750 40) (list 10710.0 40) (list 10710.0 20) "")
(command "-LAYER" "S" "Cables_UTP" "")
(command "-COLOR" "5")
(command "-TEXT" "S" "Standard" "J" "C" (list 10765 195.0) 10 0 "5xUTP")
(command "-LAYER" "S" "Cables_UTP" "")
(command "-COLOR" "5")
(command "_.PLINE" (list 10850 350) (list 10850 -20) (list 10710.0 -20) (list 10710.0 -40) "")
(command "-LAYER" "S" "Cables_UTP" "")
(command "-COLOR" "5")
(command "-TEXT" "S" "Standard" "J" "C" (list 10865 165.0) 10 0 "3xUTP")
(command "-LAYER" "S" "Cables_UTP" "")
(command "-COLOR" "5")
(command "_.PLINE" (list 10950 350) (list 10950 -140) (list 10710.0 -140) (list 10710.0 -160) "")
(command "-LAYER" "S" "Cables_UTP" "")
(command "-COLOR" "5")
(command "-TEXT" "S" "Standard" "J" "C" (list 10965 105.0) 10 0 "2xUTP")
(command "-LAYER" "S" "Cables_UTP" "")
(command "-COLOR" "5")
(command "_.PLINE" (list 11050 350) (list 11050 -80) (list 10710.0 -80) (list 10710.0 -100) "")
(command "-LAYER" "S" "Cables_UTP" "")
(command "-COLOR" "5")
(command "-TEXT" "S" "Standard" "J" "C" (list 11065 135.0) 10 0 "12xUTP")
(command "-LAYER" "S" "Cables_UTP" "")
(command "-COLOR" "5")
(command "_.PLINE" (list 10650 550) (list 10650 100) (list 10710.0 100) (list 10710.0 80) "")
(command "-LAYER" "S" "Cables_UTP" "")
(command "-COLOR" "5")
(command "-TEXT" "S" "Standard" "J" "C" (list 10665 325.0) 10 0 "4xUTP")
(command "-LAYER" "S" "Cables_UTP" "")
(command "-COLOR" "5")
(command "_.PLINE" (list 10750 550) (list 10750 40) (list 10710.0 40) (list 10710.0 20) "")
(command "-LAYER" "S" "Cables_UTP" "")
(command "-COLOR" "5")
(command "-TEXT" "S" "Standard" "J" "C" (list 10765 295.0) 10 0 "4xUTP")
(command "-LAYER" "S" "Cables_UTP" "")
(command "-COLOR" "5")
(command "_.PLINE" (list 10850 550) (list 10850 -20) (list 10710.0 -20) (list 10710.0 -40) "")
(command "-LAYER" "S" "Cables_UTP" "")
(command "-COLOR" "5")
(command "-TEXT" "S" "Standard" "J" "C" (list 10865 265.0) 10 0 "2xUTP")
(command "-LAYER" "S" "Cables_UTP" "")
(command "-COLOR" "5")
(command "_.PLINE" (list 10950 550) (list 10950 -140) (list 10710.0 -140) (list 10710.0 -160) "")
(command "-LAYER" "S" "Cables_UTP" "")
(command "-COLOR" "5")
(command "-TEXT" "S" "Standard" "J" "C" (list 10965 205.0) 10 0 "1xUTP")
(command "-LAYER" "S" "Cables_UTP" "")
(command "-COLOR" "5")
(command "_.PLINE" (list 11050 550) (list 11050 -80) (list 10710.0 -80) (list 10710.0 -100) "")
(command "-LAYER" "S" "Cables_UTP" "")
(command "-COLOR" "5")
(command "-TEXT" "S" "Standard" "J" "C" (list 11065 235.0) 10 0 "10xUTP")
(command "-LAYER" "S" "Cables_UTP" "")
(command "-COLOR" "5")
(command "_.PLINE" (list 10650 750) (list 10650 100) (list 10710.0 100) (list 10710.0 80) "")
(command "-LAYER" "S" "Cables_UTP" "")
(command "-COLOR" "5")
(command "-TEXT" "S" "Standard" "J" "C" (list 10665 425.0) 10 0 "4xUTP")
(command "-LAYER" "S" "Cables_UTP" "")
(command "-COLOR" "5")
(command "_.PLINE" (list 10750 750) (list 10750 40) (list 10710.0 40) (list 10710.0 20) "")
(command "-LAYER" "S" "Cables_UTP" "")
(command "-COLOR" "5")
(command "-TEXT" "S" "Standard" "J" "C" (list 10765 395.0) 10 0 "4xUTP")
(command "-LAYER" "S" "Cables_UTP" "")
(command "-COLOR" "5")
(command "_.PLINE" (list 10850 750) (list 10850 -20) (list 10710.0 -20) (list 10710.0 -40) "")
(command "-LAYER" "S" "Cables_UTP" "")
(command "-COLOR" "5")
(command "-TEXT" "S" "Standard" "J" "C" (list 10865 365.0) 10 0 "2xUTP")
(command "-LAYER" "S" "Cables_UTP" "")
(command "-COLOR" "5")
(command "_.PLINE" (list 10950 750) (list 10950 -140) (list 10710.0 -140) (list 10710.0 -160) "")
(command "-LAYER" "S" "Cables_UTP" "")
(command "-COLOR" "5")
(command "-TEXT" "S" "Standard" "J" "C" (list 10965 305.0) 10 0 "1xUTP")
(command "-LAYER" "S" "Cables_UTP" "")
(command "-COLOR" "5")
(command "_.PLINE" (list 11050 750) (list 11050 -80) (list 10710.0 -80) (list 10710.0 -100) "")
(command "-LAYER" "S" "Cables_UTP" "")
(command "-COLOR" "5")
(command "-TEXT" "S" "Standard" "J" "C" (list 11065 335.0) 10 0 "10xUTP")
(command "-LAYER" "S" "Cables_UTP" "")
(command "-COLOR" "5")
(command "_.PLINE" (list 10650 950) (list 10650 100) (list 10710.0 100) (list 10710.0 80) "")
(command "-LAYER" "S" "Cables_UTP" "")
(command "-COLOR" "5")
(command "-TEXT" "S" "Standard" "J" "C" (list 10665 525.0) 10 0 "4xUTP")
(command "-LAYER" "S" "Cables_UTP" "")
(command "-COLOR" "5")
(command "_.PLINE" (list 10750 950) (list 10750 40) (list 10710.0 40) (list 10710.0 20) "")
(command "-LAYER" "S" "Cables_UTP" "")
(command "-COLOR" "5")
(command "-TEXT" "S" "Standard" "J" "C" (list 10765 495.0) 10 0 "4xUTP")
(command "-LAYER" "S" "Cables_UTP" "")
(command "-COLOR" "5")
(command "_.PLINE" (list 10850 950) (list 10850 -20) (list 10710.0 -20) (list 10710.0 -40) "")
(command "-LAYER" "S" "Cables_UTP" "")
(command "-COLOR" "5")
(command "-TEXT" "S" "Standard" "J" "C" (list 10865 465.0) 10 0 "2xUTP")
(command "-LAYER" "S" "Cables_UTP" "")
(command "-COLOR" "5")
(command "_.PLINE" (list 10950 950) (list 10950 -140) (list 10710.0 -140) (list 10710.0 -160) "")
(command "-LAYER" "S" "Cables_UTP" "")
(command "-COLOR" "5")
(command "-TEXT" "S" "Standard" "J" "C" (list 10965 405.0) 10 0 "1xUTP")
(command "-LAYER" "S" "Cables_UTP" "")
(command "-COLOR" "5")
(command "_.PLINE" (list 11050 950) (list 11050 -80) (list 10710.0 -80) (list 10710.0 -100) "")
(command "-LAYER" "S" "Cables_UTP" "")
(command "-COLOR" "5")
(command "-TEXT" "S" "Standard" "J" "C" (list 11065 435.0) 10 0 "10xUTP")
(command "-LAYER" "S" "Cables_UTP" "")
(command "-COLOR" "5")
(command "_.PLINE" (list 10650 1150) (list 10650 100) (list 10710.0 100) (list 10710.0 80) "")
(command "-LAYER" "S" "Cables_UTP" "")
(command "-COLOR" "5")
(command "-TEXT" "S" "Standard" "J" "C" (list 10665 625.0) 10 0 "4xUTP")
(command "-LAYER" "S" "Cables_UTP" "")
(command "-COLOR" "5")
(command "_.PLINE" (list 10750 1150) (list 10750 40) (list 10710.0 40) (list 10710.0 20) "")
(command "-LAYER" "S" "Cables_UTP" "")
(command "-COLOR" "5")
(command "-TEXT" "S" "Standard" "J" "C" (list 10765 595.0) 10 0 "4xUTP")
(command "-LAYER" "S" "Cables_UTP" "")
(command "-COLOR" "5")
(command "_.PLINE" (list 10850 1150) (list 10850 -20) (list 10710.0 -20) (list 10710.0 -40) "")
(command "-LAYER" "S" "Cables_UTP" "")
(command "-COLOR" "5")
(command "-TEXT" "S" "Standard" "J" "C" (list 10865 565.0) 10 0 "2xUTP")
(command "-LAYER" "S" "Cables_UTP" "")
(command "-COLOR" "5")
(command "_.PLINE" (list 10950 1150) (list 10950 -140) (list 10710.0 -140) (list 10710.0 -160) "")
(command "-LAYER" "S" "Cables_UTP" "")
(command "-COLOR" "5")
(command "-TEXT" "S" "Standard" "J" "C" (list 10965 505.0) 10 0 "1xUTP")
(command "-LAYER" "S" "Cables_UTP" "")
(command "-COLOR" "5")
(command "_.PLINE" (list 11050 1150) (list 11050 -80) (list 10710.0 -80) (list 10710.0 -100) "")
(command "-LAYER" "S" "Cables_UTP" "")
(command "-COLOR" "5")
(command "-TEXT" "S" "Standard" "J" "C" (list 11065 535.0) 10 0 "10xUTP")
(command "-LAYER" "S" "Cables_UTP" "")
(command "-COLOR" "5")
(command "_.PLINE" (list 10650 1350) (list 10650 100) (list 10710.0 100) (list 10710.0 80) "")
(command "-LAYER" "S" "Cables_UTP" "")
(command "-COLOR" "5")
(command "-TEXT" "S" "Standard" "J" "C" (list 10665 725.0) 10 0 "4xUTP")
(command "-LAYER" "S" "Cables_UTP" "")
(command "-COLOR" "5")
(command "_.PLINE" (list 10750 1350) (list 10750 40) (list 10710.0 40) (list 10710.0 20) "")
(command "-LAYER" "S" "Cables_UTP" "")
(command "-COLOR" "5")
(command "-TEXT" "S" "Standard" "J" "C" (list 10765 695.0) 10 0 "4xUTP")
(command "-LAYER" "S" "Cables_UTP" "")
(command "-COLOR" "5")
(command "_.PLINE" (list 10850 1350) (list 10850 -20) (list 10710.0 -20) (list 10710.0 -40) "")
(command "-LAYER" "S" "Cables_UTP" "")
(command "-COLOR" "5")
(command "-TEXT" "S" "Standard" "J" "C" (list 10865 665.0) 10 0 "2xUTP")
(command "-LAYER" "S" "Cables_UTP" "")
(command "-COLOR" "5")
(command "_.PLINE" (list 10950 1350) (list 10950 -140) (list 10710.0 -140) (list 10710.0 -160) "")
(command "-LAYER" "S" "Cables_UTP" "")
(command "-COLOR" "5")
(command "-TEXT" "S" "Standard" "J" "C" (list 10965 605.0) 10 0 "1xUTP")
(command "-LAYER" "S" "Cables_UTP" "")
(command "-COLOR" "5")
(command "_.PLINE" (list 11050 1350) (list 11050 -80) (list 10710.0 -80) (list 10710.0 -100) "")
(command "-LAYER" "S" "Cables_UTP" "")
(command "-COLOR" "5")
(command "-TEXT" "S" "Standard" "J" "C" (list 11065 635.0) 10 0 "10xUTP")
(command "-LAYER" "S" "Cables_UTP" "")
(command "-COLOR" "5")
(command "_.PLINE" (list 10650 1550) (list 10650 100) (list 10710.0 100) (list 10710.0 80) "")
(command "-LAYER" "S" "Cables_UTP" "")
(command "-COLOR" "5")
(command "-TEXT" "S" "Standard" "J" "C" (list 10665 825.0) 10 0 "2xUTP")
(command "-LAYER" "S" "Cables_UTP" "")
(command "-COLOR" "5")
(command "_.PLINE" (list 10750 1550) (list 10750 40) (list 10710.0 40) (list 10710.0 20) "")
(command "-LAYER" "S" "Cables_UTP" "")
(command "-COLOR" "5")
(command "-TEXT" "S" "Standard" "J" "C" (list 10765 795.0) 10 0 "2xUTP")
(command "-LAYER" "S" "Cables_UTP" "")
(command "-COLOR" "5")
(command "_.PLINE" (list 10850 1550) (list 10850 -20) (list 10710.0 -20) (list 10710.0 -40) "")
(command "-LAYER" "S" "Cables_UTP" "")
(command "-COLOR" "5")
(command "-TEXT" "S" "Standard" "J" "C" (list 10865 765.0) 10 0 "1xUTP")
(command "-LAYER" "S" "Cables_UTP" "")
(command "-COLOR" "5")
(command "_.PLINE" (list 10950 1550) (list 10950 -140) (list 10710.0 -140) (list 10710.0 -160) "")
(command "-LAYER" "S" "Cables_UTP" "")
(command "-COLOR" "5")
(command "-TEXT" "S" "Standard" "J" "C" (list 10965 705.0) 10 0 "1xUTP")
(command "-LAYER" "S" "Cables_UTP" "")
(command "-COLOR" "5")
(command "_.PLINE" (list 11050 1550) (list 11050 -80) (list 10710.0 -80) (list 10710.0 -100) "")
(command "-LAYER" "S" "Cables_UTP" "")
(command "-COLOR" "5")
(command "-TEXT" "S" "Standard" "J" "C" (list 11065 735.0) 10 0 "6xUTP")
(command "-LAYER" "S" "Cables_UTP" "")
(command "-COLOR" "5")
(command "_.PLINE" (list 11700 150) (list 11700 40) (list 11760.0 40) (list 11760.0 20) "")
(command "-LAYER" "S" "Cables_UTP" "")
(command "-COLOR" "5")
(command "-TEXT" "S" "Standard" "J" "C" (list 11715 95.0) 10 0 "1xUTP")
(command "-LAYER" "S" "Cables_UTP" "")
(command "-COLOR" "5")
(command "_.PLINE" (list 11800 150) (list 11800 -140) (list 11760.0 -140) (list 11760.0 -160) "")
(command "-LAYER" "S" "Cables_UTP" "")
(command "-COLOR" "5")
(command "-TEXT" "S" "Standard" "J" "C" (list 11815 5.0) 10 0 "1xUTP")
(command "-LAYER" "S" "Cables_UTP" "")
(command "-COLOR" "5")
(command "_.PLINE" (list 11900 150) (list 11900 -80) (list 11760.0 -80) (list 11760.0 -100) "")
(command "-LAYER" "S" "Cables_UTP" "")
(command "-COLOR" "5")
(command "-TEXT" "S" "Standard" "J" "C" (list 11915 35.0) 10 0 "3xUTP")
(command "-LAYER" "S" "Cables_UTP" "")
(command "-COLOR" "5")
(command "_.PLINE" (list 11700 350) (list 11700 100) (list 11760.0 100) (list 11760.0 80) "")
(command "-LAYER" "S" "Cables_UTP" "")
(command "-COLOR" "5")
(command "-TEXT" "S" "Standard" "J" "C" (list 11715 225.0) 10 0 "5xUTP")
(command "-LAYER" "S" "Cables_UTP" "")
(command "-COLOR" "5")
(command "_.PLINE" (list 11800 350) (list 11800 40) (list 11760.0 40) (list 11760.0 20) "")
(command "-LAYER" "S" "Cables_UTP" "")
(command "-COLOR" "5")
(command "-TEXT" "S" "Standard" "J" "C" (list 11815 195.0) 10 0 "6xUTP")
(command "-LAYER" "S" "Cables_UTP" "")
(command "-COLOR" "5")
(command "_.PLINE" (list 11900 350) (list 11900 -20) (list 11760.0 -20) (list 11760.0 -40) "")
(command "-LAYER" "S" "Cables_UTP" "")
(command "-COLOR" "5")
(command "-TEXT" "S" "Standard" "J" "C" (list 11915 165.0) 10 0 "4xUTP")
(command "-LAYER" "S" "Cables_UTP" "")
(command "-COLOR" "5")
(command "_.PLINE" (list 12000 350) (list 12000 -140) (list 11760.0 -140) (list 11760.0 -160) "")
(command "-LAYER" "S" "Cables_UTP" "")
(command "-COLOR" "5")
(command "-TEXT" "S" "Standard" "J" "C" (list 12015 105.0) 10 0 "2xUTP")
(command "-LAYER" "S" "Cables_UTP" "")
(command "-COLOR" "5")
(command "_.PLINE" (list 12100 350) (list 12100 -80) (list 11760.0 -80) (list 11760.0 -100) "")
(command "-LAYER" "S" "Cables_UTP" "")
(command "-COLOR" "5")
(command "-TEXT" "S" "Standard" "J" "C" (list 12115 135.0) 10 0 "14xUTP")
(command "-LAYER" "S" "Cables_UTP" "")
(command "-COLOR" "5")
(command "_.PLINE" (list 11700 550) (list 11700 100) (list 11760.0 100) (list 11760.0 80) "")
(command "-LAYER" "S" "Cables_UTP" "")
(command "-COLOR" "5")
(command "-TEXT" "S" "Standard" "J" "C" (list 11715 325.0) 10 0 "4xUTP")
(command "-LAYER" "S" "Cables_UTP" "")
(command "-COLOR" "5")
(command "_.PLINE" (list 11800 550) (list 11800 40) (list 11760.0 40) (list 11760.0 20) "")
(command "-LAYER" "S" "Cables_UTP" "")
(command "-COLOR" "5")
(command "-TEXT" "S" "Standard" "J" "C" (list 11815 295.0) 10 0 "4xUTP")
(command "-LAYER" "S" "Cables_UTP" "")
(command "-COLOR" "5")
(command "_.PLINE" (list 11900 550) (list 11900 -20) (list 11760.0 -20) (list 11760.0 -40) "")
(command "-LAYER" "S" "Cables_UTP" "")
(command "-COLOR" "5")
(command "-TEXT" "S" "Standard" "J" "C" (list 11915 265.0) 10 0 "2xUTP")
(command "-LAYER" "S" "Cables_UTP" "")
(command "-COLOR" "5")
(command "_.PLINE" (list 12000 550) (list 12000 -140) (list 11760.0 -140) (list 11760.0 -160) "")
(command "-LAYER" "S" "Cables_UTP" "")
(command "-COLOR" "5")
(command "-TEXT" "S" "Standard" "J" "C" (list 12015 205.0) 10 0 "1xUTP")
(command "-LAYER" "S" "Cables_UTP" "")
(command "-COLOR" "5")
(command "_.PLINE" (list 12100 550) (list 12100 -80) (list 11760.0 -80) (list 11760.0 -100) "")
(command "-LAYER" "S" "Cables_UTP" "")
(command "-COLOR" "5")
(command "-TEXT" "S" "Standard" "J" "C" (list 12115 235.0) 10 0 "10xUTP")
(command "-LAYER" "S" "Cables_UTP" "")
(command "-COLOR" "5")
(command "_.PLINE" (list 11700 750) (list 11700 100) (list 11760.0 100) (list 11760.0 80) "")
(command "-LAYER" "S" "Cables_UTP" "")
(command "-COLOR" "5")
(command "-TEXT" "S" "Standard" "J" "C" (list 11715 425.0) 10 0 "4xUTP")
(command "-LAYER" "S" "Cables_UTP" "")
(command "-COLOR" "5")
(command "_.PLINE" (list 11800 750) (list 11800 40) (list 11760.0 40) (list 11760.0 20) "")
(command "-LAYER" "S" "Cables_UTP" "")
(command "-COLOR" "5")
(command "-TEXT" "S" "Standard" "J" "C" (list 11815 395.0) 10 0 "4xUTP")
(command "-LAYER" "S" "Cables_UTP" "")
(command "-COLOR" "5")
(command "_.PLINE" (list 11900 750) (list 11900 -20) (list 11760.0 -20) (list 11760.0 -40) "")
(command "-LAYER" "S" "Cables_UTP" "")
(command "-COLOR" "5")
(command "-TEXT" "S" "Standard" "J" "C" (list 11915 365.0) 10 0 "2xUTP")
(command "-LAYER" "S" "Cables_UTP" "")
(command "-COLOR" "5")
(command "_.PLINE" (list 12000 750) (list 12000 -140) (list 11760.0 -140) (list 11760.0 -160) "")
(command "-LAYER" "S" "Cables_UTP" "")
(command "-COLOR" "5")
(command "-TEXT" "S" "Standard" "J" "C" (list 12015 305.0) 10 0 "1xUTP")
(command "-LAYER" "S" "Cables_UTP" "")
(command "-COLOR" "5")
(command "_.PLINE" (list 12100 750) (list 12100 -80) (list 11760.0 -80) (list 11760.0 -100) "")
(command "-LAYER" "S" "Cables_UTP" "")
(command "-COLOR" "5")
(command "-TEXT" "S" "Standard" "J" "C" (list 12115 335.0) 10 0 "10xUTP")
(command "-LAYER" "S" "Cables_UTP" "")
(command "-COLOR" "5")
(command "_.PLINE" (list 11700 950) (list 11700 100) (list 11760.0 100) (list 11760.0 80) "")
(command "-LAYER" "S" "Cables_UTP" "")
(command "-COLOR" "5")
(command "-TEXT" "S" "Standard" "J" "C" (list 11715 525.0) 10 0 "4xUTP")
(command "-LAYER" "S" "Cables_UTP" "")
(command "-COLOR" "5")
(command "_.PLINE" (list 11800 950) (list 11800 40) (list 11760.0 40) (list 11760.0 20) "")
(command "-LAYER" "S" "Cables_UTP" "")
(command "-COLOR" "5")
(command "-TEXT" "S" "Standard" "J" "C" (list 11815 495.0) 10 0 "4xUTP")
(command "-LAYER" "S" "Cables_UTP" "")
(command "-COLOR" "5")
(command "_.PLINE" (list 11900 950) (list 11900 -20) (list 11760.0 -20) (list 11760.0 -40) "")
(command "-LAYER" "S" "Cables_UTP" "")
(command "-COLOR" "5")
(command "-TEXT" "S" "Standard" "J" "C" (list 11915 465.0) 10 0 "2xUTP")
(command "-LAYER" "S" "Cables_UTP" "")
(command "-COLOR" "5")
(command "_.PLINE" (list 12000 950) (list 12000 -140) (list 11760.0 -140) (list 11760.0 -160) "")
(command "-LAYER" "S" "Cables_UTP" "")
(command "-COLOR" "5")
(command "-TEXT" "S" "Standard" "J" "C" (list 12015 405.0) 10 0 "1xUTP")
(command "-LAYER" "S" "Cables_UTP" "")
(command "-COLOR" "5")
(command "_.PLINE" (list 12100 950) (list 12100 -80) (list 11760.0 -80) (list 11760.0 -100) "")
(command "-LAYER" "S" "Cables_UTP" "")
(command "-COLOR" "5")
(command "-TEXT" "S" "Standard" "J" "C" (list 12115 435.0) 10 0 "10xUTP")
(command "-LAYER" "S" "Cables_UTP" "")
(command "-COLOR" "5")
(command "_.PLINE" (list 11700 1150) (list 11700 100) (list 11760.0 100) (list 11760.0 80) "")
(command "-LAYER" "S" "Cables_UTP" "")
(command "-COLOR" "5")
(command "-TEXT" "S" "Standard" "J" "C" (list 11715 625.0) 10 0 "4xUTP")
(command "-LAYER" "S" "Cables_UTP" "")
(command "-COLOR" "5")
(command "_.PLINE" (list 11800 1150) (list 11800 40) (list 11760.0 40) (list 11760.0 20) "")
(command "-LAYER" "S" "Cables_UTP" "")
(command "-COLOR" "5")
(command "-TEXT" "S" "Standard" "J" "C" (list 11815 595.0) 10 0 "4xUTP")
(command "-LAYER" "S" "Cables_UTP" "")
(command "-COLOR" "5")
(command "_.PLINE" (list 11900 1150) (list 11900 -20) (list 11760.0 -20) (list 11760.0 -40) "")
(command "-LAYER" "S" "Cables_UTP" "")
(command "-COLOR" "5")
(command "-TEXT" "S" "Standard" "J" "C" (list 11915 565.0) 10 0 "2xUTP")
(command "-LAYER" "S" "Cables_UTP" "")
(command "-COLOR" "5")
(command "_.PLINE" (list 12000 1150) (list 12000 -140) (list 11760.0 -140) (list 11760.0 -160) "")
(command "-LAYER" "S" "Cables_UTP" "")
(command "-COLOR" "5")
(command "-TEXT" "S" "Standard" "J" "C" (list 12015 505.0) 10 0 "1xUTP")
(command "-LAYER" "S" "Cables_UTP" "")
(command "-COLOR" "5")
(command "_.PLINE" (list 12100 1150) (list 12100 -80) (list 11760.0 -80) (list 11760.0 -100) "")
(command "-LAYER" "S" "Cables_UTP" "")
(command "-COLOR" "5")
(command "-TEXT" "S" "Standard" "J" "C" (list 12115 535.0) 10 0 "10xUTP")
(command "-LAYER" "S" "Cables_UTP" "")
(command "-COLOR" "5")
(command "_.PLINE" (list 11700 1350) (list 11700 100) (list 11760.0 100) (list 11760.0 80) "")
(command "-LAYER" "S" "Cables_UTP" "")
(command "-COLOR" "5")
(command "-TEXT" "S" "Standard" "J" "C" (list 11715 725.0) 10 0 "4xUTP")
(command "-LAYER" "S" "Cables_UTP" "")
(command "-COLOR" "5")
(command "_.PLINE" (list 11800 1350) (list 11800 40) (list 11760.0 40) (list 11760.0 20) "")
(command "-LAYER" "S" "Cables_UTP" "")
(command "-COLOR" "5")
(command "-TEXT" "S" "Standard" "J" "C" (list 11815 695.0) 10 0 "4xUTP")
(command "-LAYER" "S" "Cables_UTP" "")
(command "-COLOR" "5")
(command "_.PLINE" (list 11900 1350) (list 11900 -20) (list 11760.0 -20) (list 11760.0 -40) "")
(command "-LAYER" "S" "Cables_UTP" "")
(command "-COLOR" "5")
(command "-TEXT" "S" "Standard" "J" "C" (list 11915 665.0) 10 0 "2xUTP")
(command "-LAYER" "S" "Cables_UTP" "")
(command "-COLOR" "5")
(command "_.PLINE" (list 12000 1350) (list 12000 -140) (list 11760.0 -140) (list 11760.0 -160) "")
(command "-LAYER" "S" "Cables_UTP" "")
(command "-COLOR" "5")
(command "-TEXT" "S" "Standard" "J" "C" (list 12015 605.0) 10 0 "1xUTP")
(command "-LAYER" "S" "Cables_UTP" "")
(command "-COLOR" "5")
(command "_.PLINE" (list 12100 1350) (list 12100 -80) (list 11760.0 -80) (list 11760.0 -100) "")
(command "-LAYER" "S" "Cables_UTP" "")
(command "-COLOR" "5")
(command "-TEXT" "S" "Standard" "J" "C" (list 12115 635.0) 10 0 "10xUTP")
(command "-LAYER" "S" "Cables_UTP" "")
(command "-COLOR" "5")
(command "_.PLINE" (list 11700 1550) (list 11700 100) (list 11760.0 100) (list 11760.0 80) "")
(command "-LAYER" "S" "Cables_UTP" "")
(command "-COLOR" "5")
(command "-TEXT" "S" "Standard" "J" "C" (list 11715 825.0) 10 0 "2xUTP")
(command "-LAYER" "S" "Cables_UTP" "")
(command "-COLOR" "5")
(command "_.PLINE" (list 11800 1550) (list 11800 40) (list 11760.0 40) (list 11760.0 20) "")
(command "-LAYER" "S" "Cables_UTP" "")
(command "-COLOR" "5")
(command "-TEXT" "S" "Standard" "J" "C" (list 11815 795.0) 10 0 "2xUTP")
(command "-LAYER" "S" "Cables_UTP" "")
(command "-COLOR" "5")
(command "_.PLINE" (list 11900 1550) (list 11900 -20) (list 11760.0 -20) (list 11760.0 -40) "")
(command "-LAYER" "S" "Cables_UTP" "")
(command "-COLOR" "5")
(command "-TEXT" "S" "Standard" "J" "C" (list 11915 765.0) 10 0 "1xUTP")
(command "-LAYER" "S" "Cables_UTP" "")
(command "-COLOR" "5")
(command "_.PLINE" (list 12000 1550) (list 12000 -140) (list 11760.0 -140) (list 11760.0 -160) "")
(command "-LAYER" "S" "Cables_UTP" "")
(command "-COLOR" "5")
(command "-TEXT" "S" "Standard" "J" "C" (list 12015 705.0) 10 0 "1xUTP")
(command "-LAYER" "S" "Cables_UTP" "")
(command "-COLOR" "5")
(command "_.PLINE" (list 12100 1550) (list 12100 -80) (list 11760.0 -80) (list 11760.0 -100) "")
(command "-LAYER" "S" "Cables_UTP" "")
(command "-COLOR" "5")
(command "-TEXT" "S" "Standard" "J" "C" (list 12115 735.0) 10 0 "6xUTP")
(command "-LAYER" "S" "Cables_UTP" "")
(command "-COLOR" "5")
(command "_.PLINE" (list 12750 150) (list 12750 100) (list 12810.0 100) (list 12810.0 80) "")
(command "-LAYER" "S" "Cables_UTP" "")
(command "-COLOR" "5")
(command "-TEXT" "S" "Standard" "J" "C" (list 12765 125.0) 10 0 "2xUTP")
(command "-LAYER" "S" "Cables_UTP" "")
(command "-COLOR" "5")
(command "_.PLINE" (list 12850 150) (list 12850 40) (list 12810.0 40) (list 12810.0 20) "")
(command "-LAYER" "S" "Cables_UTP" "")
(command "-COLOR" "5")
(command "-TEXT" "S" "Standard" "J" "C" (list 12865 95.0) 10 0 "3xUTP")
(command "-LAYER" "S" "Cables_UTP" "")
(command "-COLOR" "5")
(command "_.PLINE" (list 12950 150) (list 12950 -20) (list 12810.0 -20) (list 12810.0 -40) "")
(command "-LAYER" "S" "Cables_UTP" "")
(command "-COLOR" "5")
(command "-TEXT" "S" "Standard" "J" "C" (list 12965 65.0) 10 0 "2xUTP")
(command "-LAYER" "S" "Cables_UTP" "")
(command "-COLOR" "5")
(command "_.PLINE" (list 13050 150) (list 13050 -140) (list 12810.0 -140) (list 12810.0 -160) "")
(command "-LAYER" "S" "Cables_UTP" "")
(command "-COLOR" "5")
(command "-TEXT" "S" "Standard" "J" "C" (list 13065 5.0) 10 0 "1xUTP")
(command "-LAYER" "S" "Cables_UTP" "")
(command "-COLOR" "5")
(command "_.PLINE" (list 13150 150) (list 13150 -80) (list 12810.0 -80) (list 12810.0 -100) "")
(command "-LAYER" "S" "Cables_UTP" "")
(command "-COLOR" "5")
(command "-TEXT" "S" "Standard" "J" "C" (list 13165 35.0) 10 0 "7xUTP")
(command "-LAYER" "S" "Cables_UTP" "")
(command "-COLOR" "5")
(command "_.PLINE" (list 12750 350) (list 12750 100) (list 12810.0 100) (list 12810.0 80) "")
(command "-LAYER" "S" "Cables_UTP" "")
(command "-COLOR" "5")
(command "-TEXT" "S" "Standard" "J" "C" (list 12765 225.0) 10 0 "4xUTP")
(command "-LAYER" "S" "Cables_UTP" "")
(command "-COLOR" "5")
(command "_.PLINE" (list 12850 350) (list 12850 40) (list 12810.0 40) (list 12810.0 20) "")
(command "-LAYER" "S" "Cables_UTP" "")
(command "-COLOR" "5")
(command "-TEXT" "S" "Standard" "J" "C" (list 12865 195.0) 10 0 "5xUTP")
(command "-LAYER" "S" "Cables_UTP" "")
(command "-COLOR" "5")
(command "_.PLINE" (list 12950 350) (list 12950 -20) (list 12810.0 -20) (list 12810.0 -40) "")
(command "-LAYER" "S" "Cables_UTP" "")
(command "-COLOR" "5")
(command "-TEXT" "S" "Standard" "J" "C" (list 12965 165.0) 10 0 "3xUTP")
(command "-LAYER" "S" "Cables_UTP" "")
(command "-COLOR" "5")
(command "_.PLINE" (list 13050 350) (list 13050 -140) (list 12810.0 -140) (list 12810.0 -160) "")
(command "-LAYER" "S" "Cables_UTP" "")
(command "-COLOR" "5")
(command "-TEXT" "S" "Standard" "J" "C" (list 13065 105.0) 10 0 "2xUTP")
(command "-LAYER" "S" "Cables_UTP" "")
(command "-COLOR" "5")
(command "_.PLINE" (list 13150 350) (list 13150 -80) (list 12810.0 -80) (list 12810.0 -100) "")
(command "-LAYER" "S" "Cables_UTP" "")
(command "-COLOR" "5")
(command "-TEXT" "S" "Standard" "J" "C" (list 13165 135.0) 10 0 "12xUTP")
(command "-LAYER" "S" "Cables_UTP" "")
(command "-COLOR" "5")
(command "_.PLINE" (list 12750 550) (list 12750 100) (list 12810.0 100) (list 12810.0 80) "")
(command "-LAYER" "S" "Cables_UTP" "")
(command "-COLOR" "5")
(command "-TEXT" "S" "Standard" "J" "C" (list 12765 325.0) 10 0 "4xUTP")
(command "-LAYER" "S" "Cables_UTP" "")
(command "-COLOR" "5")
(command "_.PLINE" (list 12850 550) (list 12850 40) (list 12810.0 40) (list 12810.0 20) "")
(command "-LAYER" "S" "Cables_UTP" "")
(command "-COLOR" "5")
(command "-TEXT" "S" "Standard" "J" "C" (list 12865 295.0) 10 0 "4xUTP")
(command "-LAYER" "S" "Cables_UTP" "")
(command "-COLOR" "5")
(command "_.PLINE" (list 12950 550) (list 12950 -20) (list 12810.0 -20) (list 12810.0 -40) "")
(command "-LAYER" "S" "Cables_UTP" "")
(command "-COLOR" "5")
(command "-TEXT" "S" "Standard" "J" "C" (list 12965 265.0) 10 0 "2xUTP")
(command "-LAYER" "S" "Cables_UTP" "")
(command "-COLOR" "5")
(command "_.PLINE" (list 13050 550) (list 13050 -140) (list 12810.0 -140) (list 12810.0 -160) "")
(command "-LAYER" "S" "Cables_UTP" "")
(command "-COLOR" "5")
(command "-TEXT" "S" "Standard" "J" "C" (list 13065 205.0) 10 0 "1xUTP")
(command "-LAYER" "S" "Cables_UTP" "")
(command "-COLOR" "5")
(command "_.PLINE" (list 13150 550) (list 13150 -80) (list 12810.0 -80) (list 12810.0 -100) "")
(command "-LAYER" "S" "Cables_UTP" "")
(command "-COLOR" "5")
(command "-TEXT" "S" "Standard" "J" "C" (list 13165 235.0) 10 0 "10xUTP")
(command "-LAYER" "S" "Cables_UTP" "")
(command "-COLOR" "5")
(command "_.PLINE" (list 12750 750) (list 12750 100) (list 12810.0 100) (list 12810.0 80) "")
(command "-LAYER" "S" "Cables_UTP" "")
(command "-COLOR" "5")
(command "-TEXT" "S" "Standard" "J" "C" (list 12765 425.0) 10 0 "4xUTP")
(command "-LAYER" "S" "Cables_UTP" "")
(command "-COLOR" "5")
(command "_.PLINE" (list 12850 750) (list 12850 40) (list 12810.0 40) (list 12810.0 20) "")
(command "-LAYER" "S" "Cables_UTP" "")
(command "-COLOR" "5")
(command "-TEXT" "S" "Standard" "J" "C" (list 12865 395.0) 10 0 "4xUTP")
(command "-LAYER" "S" "Cables_UTP" "")
(command "-COLOR" "5")
(command "_.PLINE" (list 12950 750) (list 12950 -20) (list 12810.0 -20) (list 12810.0 -40) "")
(command "-LAYER" "S" "Cables_UTP" "")
(command "-COLOR" "5")
(command "-TEXT" "S" "Standard" "J" "C" (list 12965 365.0) 10 0 "2xUTP")
(command "-LAYER" "S" "Cables_UTP" "")
(command "-COLOR" "5")
(command "_.PLINE" (list 13050 750) (list 13050 -140) (list 12810.0 -140) (list 12810.0 -160) "")
(command "-LAYER" "S" "Cables_UTP" "")
(command "-COLOR" "5")
(command "-TEXT" "S" "Standard" "J" "C" (list 13065 305.0) 10 0 "1xUTP")
(command "-LAYER" "S" "Cables_UTP" "")
(command "-COLOR" "5")
(command "_.PLINE" (list 13150 750) (list 13150 -80) (list 12810.0 -80) (list 12810.0 -100) "")
(command "-LAYER" "S" "Cables_UTP" "")
(command "-COLOR" "5")
(command "-TEXT" "S" "Standard" "J" "C" (list 13165 335.0) 10 0 "10xUTP")
(command "-LAYER" "S" "Cables_UTP" "")
(command "-COLOR" "5")
(command "_.PLINE" (list 12750 950) (list 12750 100) (list 12810.0 100) (list 12810.0 80) "")
(command "-LAYER" "S" "Cables_UTP" "")
(command "-COLOR" "5")
(command "-TEXT" "S" "Standard" "J" "C" (list 12765 525.0) 10 0 "4xUTP")
(command "-LAYER" "S" "Cables_UTP" "")
(command "-COLOR" "5")
(command "_.PLINE" (list 12850 950) (list 12850 40) (list 12810.0 40) (list 12810.0 20) "")
(command "-LAYER" "S" "Cables_UTP" "")
(command "-COLOR" "5")
(command "-TEXT" "S" "Standard" "J" "C" (list 12865 495.0) 10 0 "4xUTP")
(command "-LAYER" "S" "Cables_UTP" "")
(command "-COLOR" "5")
(command "_.PLINE" (list 12950 950) (list 12950 -20) (list 12810.0 -20) (list 12810.0 -40) "")
(command "-LAYER" "S" "Cables_UTP" "")
(command "-COLOR" "5")
(command "-TEXT" "S" "Standard" "J" "C" (list 12965 465.0) 10 0 "2xUTP")
(command "-LAYER" "S" "Cables_UTP" "")
(command "-COLOR" "5")
(command "_.PLINE" (list 13050 950) (list 13050 -140) (list 12810.0 -140) (list 12810.0 -160) "")
(command "-LAYER" "S" "Cables_UTP" "")
(command "-COLOR" "5")
(command "-TEXT" "S" "Standard" "J" "C" (list 13065 405.0) 10 0 "1xUTP")
(command "-LAYER" "S" "Cables_UTP" "")
(command "-COLOR" "5")
(command "_.PLINE" (list 13150 950) (list 13150 -80) (list 12810.0 -80) (list 12810.0 -100) "")
(command "-LAYER" "S" "Cables_UTP" "")
(command "-COLOR" "5")
(command "-TEXT" "S" "Standard" "J" "C" (list 13165 435.0) 10 0 "10xUTP")
(command "-LAYER" "S" "Cables_UTP" "")
(command "-COLOR" "5")
(command "_.PLINE" (list 12750 1150) (list 12750 100) (list 12810.0 100) (list 12810.0 80) "")
(command "-LAYER" "S" "Cables_UTP" "")
(command "-COLOR" "5")
(command "-TEXT" "S" "Standard" "J" "C" (list 12765 625.0) 10 0 "4xUTP")
(command "-LAYER" "S" "Cables_UTP" "")
(command "-COLOR" "5")
(command "_.PLINE" (list 12850 1150) (list 12850 40) (list 12810.0 40) (list 12810.0 20) "")
(command "-LAYER" "S" "Cables_UTP" "")
(command "-COLOR" "5")
(command "-TEXT" "S" "Standard" "J" "C" (list 12865 595.0) 10 0 "4xUTP")
(command "-LAYER" "S" "Cables_UTP" "")
(command "-COLOR" "5")
(command "_.PLINE" (list 12950 1150) (list 12950 -20) (list 12810.0 -20) (list 12810.0 -40) "")
(command "-LAYER" "S" "Cables_UTP" "")
(command "-COLOR" "5")
(command "-TEXT" "S" "Standard" "J" "C" (list 12965 565.0) 10 0 "2xUTP")
(command "-LAYER" "S" "Cables_UTP" "")
(command "-COLOR" "5")
(command "_.PLINE" (list 13050 1150) (list 13050 -140) (list 12810.0 -140) (list 12810.0 -160) "")
(command "-LAYER" "S" "Cables_UTP" "")
(command "-COLOR" "5")
(command "-TEXT" "S" "Standard" "J" "C" (list 13065 505.0) 10 0 "1xUTP")
(command "-LAYER" "S" "Cables_UTP" "")
(command "-COLOR" "5")
(command "_.PLINE" (list 13150 1150) (list 13150 -80) (list 12810.0 -80) (list 12810.0 -100) "")
(command "-LAYER" "S" "Cables_UTP" "")
(command "-COLOR" "5")
(command "-TEXT" "S" "Standard" "J" "C" (list 13165 535.0) 10 0 "10xUTP")
(command "-LAYER" "S" "Cables_UTP" "")
(command "-COLOR" "5")
(command "_.PLINE" (list 12750 1350) (list 12750 100) (list 12810.0 100) (list 12810.0 80) "")
(command "-LAYER" "S" "Cables_UTP" "")
(command "-COLOR" "5")
(command "-TEXT" "S" "Standard" "J" "C" (list 12765 725.0) 10 0 "4xUTP")
(command "-LAYER" "S" "Cables_UTP" "")
(command "-COLOR" "5")
(command "_.PLINE" (list 12850 1350) (list 12850 40) (list 12810.0 40) (list 12810.0 20) "")
(command "-LAYER" "S" "Cables_UTP" "")
(command "-COLOR" "5")
(command "-TEXT" "S" "Standard" "J" "C" (list 12865 695.0) 10 0 "4xUTP")
(command "-LAYER" "S" "Cables_UTP" "")
(command "-COLOR" "5")
(command "_.PLINE" (list 12950 1350) (list 12950 -20) (list 12810.0 -20) (list 12810.0 -40) "")
(command "-LAYER" "S" "Cables_UTP" "")
(command "-COLOR" "5")
(command "-TEXT" "S" "Standard" "J" "C" (list 12965 665.0) 10 0 "2xUTP")
(command "-LAYER" "S" "Cables_UTP" "")
(command "-COLOR" "5")
(command "_.PLINE" (list 13050 1350) (list 13050 -140) (list 12810.0 -140) (list 12810.0 -160) "")
(command "-LAYER" "S" "Cables_UTP" "")
(command "-COLOR" "5")
(command "-TEXT" "S" "Standard" "J" "C" (list 13065 605.0) 10 0 "1xUTP")
(command "-LAYER" "S" "Cables_UTP" "")
(command "-COLOR" "5")
(command "_.PLINE" (list 13150 1350) (list 13150 -80) (list 12810.0 -80) (list 12810.0 -100) "")
(command "-LAYER" "S" "Cables_UTP" "")
(command "-COLOR" "5")
(command "-TEXT" "S" "Standard" "J" "C" (list 13165 635.0) 10 0 "10xUTP")
(command "-LAYER" "S" "Cables_UTP" "")
(command "-COLOR" "5")
(command "_.PLINE" (list 12750 1550) (list 12750 100) (list 12810.0 100) (list 12810.0 80) "")
(command "-LAYER" "S" "Cables_UTP" "")
(command "-COLOR" "5")
(command "-TEXT" "S" "Standard" "J" "C" (list 12765 825.0) 10 0 "2xUTP")
(command "-LAYER" "S" "Cables_UTP" "")
(command "-COLOR" "5")
(command "_.PLINE" (list 12850 1550) (list 12850 40) (list 12810.0 40) (list 12810.0 20) "")
(command "-LAYER" "S" "Cables_UTP" "")
(command "-COLOR" "5")
(command "-TEXT" "S" "Standard" "J" "C" (list 12865 795.0) 10 0 "2xUTP")
(command "-LAYER" "S" "Cables_UTP" "")
(command "-COLOR" "5")
(command "_.PLINE" (list 12950 1550) (list 12950 -20) (list 12810.0 -20) (list 12810.0 -40) "")
(command "-LAYER" "S" "Cables_UTP" "")
(command "-COLOR" "5")
(command "-TEXT" "S" "Standard" "J" "C" (list 12965 765.0) 10 0 "1xUTP")
(command "-LAYER" "S" "Cables_UTP" "")
(command "-COLOR" "5")
(command "_.PLINE" (list 13050 1550) (list 13050 -140) (list 12810.0 -140) (list 12810.0 -160) "")
(command "-LAYER" "S" "Cables_UTP" "")
(command "-COLOR" "5")
(command "-TEXT" "S" "Standard" "J" "C" (list 13065 705.0) 10 0 "1xUTP")
(command "-LAYER" "S" "Cables_UTP" "")
(command "-COLOR" "5")
(command "_.PLINE" (list 13150 1550) (list 13150 -80) (list 12810.0 -80) (list 12810.0 -100) "")
(command "-LAYER" "S" "Cables_UTP" "")
(command "-COLOR" "5")
(command "-TEXT" "S" "Standard" "J" "C" (list 13165 735.0) 10 0 "6xUTP")
(command "-LAYER" "S" "Cables_UTP" "")
(command "-COLOR" "5")
(command "_.PLINE" (list 13800 150) (list 13800 40) (list 13860.0 40) (list 13860.0 20) "")
(command "-LAYER" "S" "Cables_UTP" "")
(command "-COLOR" "5")
(command "-TEXT" "S" "Standard" "J" "C" (list 13815 95.0) 10 0 "2xUTP")
(command "-LAYER" "S" "Cables_UTP" "")
(command "-COLOR" "5")
(command "_.PLINE" (list 13900 150) (list 13900 -20) (list 13860.0 -20) (list 13860.0 -40) "")
(command "-LAYER" "S" "Cables_UTP" "")
(command "-COLOR" "5")
(command "-TEXT" "S" "Standard" "J" "C" (list 13915 65.0) 10 0 "1xUTP")
(command "-LAYER" "S" "Cables_UTP" "")
(command "-COLOR" "5")
(command "_.PLINE" (list 14000 150) (list 14000 -140) (list 13860.0 -140) (list 13860.0 -160) "")
(command "-LAYER" "S" "Cables_UTP" "")
(command "-COLOR" "5")
(command "-TEXT" "S" "Standard" "J" "C" (list 14015 5.0) 10 0 "1xUTP")
(command "-LAYER" "S" "Cables_UTP" "")
(command "-COLOR" "5")
(command "_.PLINE" (list 14100 150) (list 14100 -80) (list 13860.0 -80) (list 13860.0 -100) "")
(command "-LAYER" "S" "Cables_UTP" "")
(command "-COLOR" "5")
(command "-TEXT" "S" "Standard" "J" "C" (list 14115 35.0) 10 0 "4xUTP")
(command "-LAYER" "S" "Cables_UTP" "")
(command "-COLOR" "5")
(command "_.PLINE" (list 13800 350) (list 13800 100) (list 13860.0 100) (list 13860.0 80) "")
(command "-LAYER" "S" "Cables_UTP" "")
(command "-COLOR" "5")
(command "-TEXT" "S" "Standard" "J" "C" (list 13815 225.0) 10 0 "9xUTP")
(command "-LAYER" "S" "Cables_UTP" "")
(command "-COLOR" "5")
(command "_.PLINE" (list 13900 350) (list 13900 40) (list 13860.0 40) (list 13860.0 20) "")
(command "-LAYER" "S" "Cables_UTP" "")
(command "-COLOR" "5")
(command "-TEXT" "S" "Standard" "J" "C" (list 13915 195.0) 10 0 "10xUTP")
(command "-LAYER" "S" "Cables_UTP" "")
(command "-COLOR" "5")
(command "_.PLINE" (list 14000 350) (list 14000 -20) (list 13860.0 -20) (list 13860.0 -40) "")
(command "-LAYER" "S" "Cables_UTP" "")
(command "-COLOR" "5")
(command "-TEXT" "S" "Standard" "J" "C" (list 14015 165.0) 10 0 "6xUTP")
(command "-LAYER" "S" "Cables_UTP" "")
(command "-COLOR" "5")
(command "_.PLINE" (list 14100 350) (list 14100 -140) (list 13860.0 -140) (list 13860.0 -160) "")
(command "-LAYER" "S" "Cables_UTP" "")
(command "-COLOR" "5")
(command "-TEXT" "S" "Standard" "J" "C" (list 14115 105.0) 10 0 "3xUTP")
(command "-LAYER" "S" "Cables_UTP" "")
(command "-COLOR" "5")
(command "_.PLINE" (list 14200 350) (list 14200 -80) (list 13860.0 -80) (list 13860.0 -100) "")
(command "-LAYER" "S" "Cables_UTP" "")
(command "-COLOR" "5")
(command "-TEXT" "S" "Standard" "J" "C" (list 14215 135.0) 10 0 "20xUTP")
(command "-LAYER" "S" "Cables_UTP" "")
(command "-COLOR" "5")
(command "_.PLINE" (list 13800 550) (list 13800 100) (list 13860.0 100) (list 13860.0 80) "")
(command "-LAYER" "S" "Cables_UTP" "")
(command "-COLOR" "5")
(command "-TEXT" "S" "Standard" "J" "C" (list 13815 325.0) 10 0 "6xUTP")
(command "-LAYER" "S" "Cables_UTP" "")
(command "-COLOR" "5")
(command "_.PLINE" (list 13900 550) (list 13900 40) (list 13860.0 40) (list 13860.0 20) "")
(command "-LAYER" "S" "Cables_UTP" "")
(command "-COLOR" "5")
(command "-TEXT" "S" "Standard" "J" "C" (list 13915 295.0) 10 0 "7xUTP")
(command "-LAYER" "S" "Cables_UTP" "")
(command "-COLOR" "5")
(command "_.PLINE" (list 14000 550) (list 14000 -20) (list 13860.0 -20) (list 13860.0 -40) "")
(command "-LAYER" "S" "Cables_UTP" "")
(command "-COLOR" "5")
(command "-TEXT" "S" "Standard" "J" "C" (list 14015 265.0) 10 0 "4xUTP")
(command "-LAYER" "S" "Cables_UTP" "")
(command "-COLOR" "5")
(command "_.PLINE" (list 14100 550) (list 14100 -140) (list 13860.0 -140) (list 13860.0 -160) "")
(command "-LAYER" "S" "Cables_UTP" "")
(command "-COLOR" "5")
(command "-TEXT" "S" "Standard" "J" "C" (list 14115 205.0) 10 0 "2xUTP")
(command "-LAYER" "S" "Cables_UTP" "")
(command "-COLOR" "5")
(command "_.PLINE" (list 14200 550) (list 14200 -80) (list 13860.0 -80) (list 13860.0 -100) "")
(command "-LAYER" "S" "Cables_UTP" "")
(command "-COLOR" "5")
(command "-TEXT" "S" "Standard" "J" "C" (list 14215 235.0) 10 0 "15xUTP")
(command "-LAYER" "S" "Cables_UTP" "")
(command "-COLOR" "5")
(command "_.PLINE" (list 13800 750) (list 13800 100) (list 13860.0 100) (list 13860.0 80) "")
(command "-LAYER" "S" "Cables_UTP" "")
(command "-COLOR" "5")
(command "-TEXT" "S" "Standard" "J" "C" (list 13815 425.0) 10 0 "6xUTP")
(command "-LAYER" "S" "Cables_UTP" "")
(command "-COLOR" "5")
(command "_.PLINE" (list 13900 750) (list 13900 40) (list 13860.0 40) (list 13860.0 20) "")
(command "-LAYER" "S" "Cables_UTP" "")
(command "-COLOR" "5")
(command "-TEXT" "S" "Standard" "J" "C" (list 13915 395.0) 10 0 "7xUTP")
(command "-LAYER" "S" "Cables_UTP" "")
(command "-COLOR" "5")
(command "_.PLINE" (list 14000 750) (list 14000 -20) (list 13860.0 -20) (list 13860.0 -40) "")
(command "-LAYER" "S" "Cables_UTP" "")
(command "-COLOR" "5")
(command "-TEXT" "S" "Standard" "J" "C" (list 14015 365.0) 10 0 "4xUTP")
(command "-LAYER" "S" "Cables_UTP" "")
(command "-COLOR" "5")
(command "_.PLINE" (list 14100 750) (list 14100 -140) (list 13860.0 -140) (list 13860.0 -160) "")
(command "-LAYER" "S" "Cables_UTP" "")
(command "-COLOR" "5")
(command "-TEXT" "S" "Standard" "J" "C" (list 14115 305.0) 10 0 "2xUTP")
(command "-LAYER" "S" "Cables_UTP" "")
(command "-COLOR" "5")
(command "_.PLINE" (list 14200 750) (list 14200 -80) (list 13860.0 -80) (list 13860.0 -100) "")
(command "-LAYER" "S" "Cables_UTP" "")
(command "-COLOR" "5")
(command "-TEXT" "S" "Standard" "J" "C" (list 14215 335.0) 10 0 "15xUTP")
(command "-LAYER" "S" "Cables_UTP" "")
(command "-COLOR" "5")
(command "_.PLINE" (list 13800 950) (list 13800 100) (list 13860.0 100) (list 13860.0 80) "")
(command "-LAYER" "S" "Cables_UTP" "")
(command "-COLOR" "5")
(command "-TEXT" "S" "Standard" "J" "C" (list 13815 525.0) 10 0 "6xUTP")
(command "-LAYER" "S" "Cables_UTP" "")
(command "-COLOR" "5")
(command "_.PLINE" (list 13900 950) (list 13900 40) (list 13860.0 40) (list 13860.0 20) "")
(command "-LAYER" "S" "Cables_UTP" "")
(command "-COLOR" "5")
(command "-TEXT" "S" "Standard" "J" "C" (list 13915 495.0) 10 0 "7xUTP")
(command "-LAYER" "S" "Cables_UTP" "")
(command "-COLOR" "5")
(command "_.PLINE" (list 14000 950) (list 14000 -20) (list 13860.0 -20) (list 13860.0 -40) "")
(command "-LAYER" "S" "Cables_UTP" "")
(command "-COLOR" "5")
(command "-TEXT" "S" "Standard" "J" "C" (list 14015 465.0) 10 0 "4xUTP")
(command "-LAYER" "S" "Cables_UTP" "")
(command "-COLOR" "5")
(command "_.PLINE" (list 14100 950) (list 14100 -140) (list 13860.0 -140) (list 13860.0 -160) "")
(command "-LAYER" "S" "Cables_UTP" "")
(command "-COLOR" "5")
(command "-TEXT" "S" "Standard" "J" "C" (list 14115 405.0) 10 0 "2xUTP")
(command "-LAYER" "S" "Cables_UTP" "")
(command "-COLOR" "5")
(command "_.PLINE" (list 14200 950) (list 14200 -80) (list 13860.0 -80) (list 13860.0 -100) "")
(command "-LAYER" "S" "Cables_UTP" "")
(command "-COLOR" "5")
(command "-TEXT" "S" "Standard" "J" "C" (list 14215 435.0) 10 0 "15xUTP")
(command "-LAYER" "S" "Cables_UTP" "")
(command "-COLOR" "5")
(command "_.PLINE" (list 13800 1150) (list 13800 100) (list 13860.0 100) (list 13860.0 80) "")
(command "-LAYER" "S" "Cables_UTP" "")
(command "-COLOR" "5")
(command "-TEXT" "S" "Standard" "J" "C" (list 13815 625.0) 10 0 "6xUTP")
(command "-LAYER" "S" "Cables_UTP" "")
(command "-COLOR" "5")
(command "_.PLINE" (list 13900 1150) (list 13900 40) (list 13860.0 40) (list 13860.0 20) "")
(command "-LAYER" "S" "Cables_UTP" "")
(command "-COLOR" "5")
(command "-TEXT" "S" "Standard" "J" "C" (list 13915 595.0) 10 0 "7xUTP")
(command "-LAYER" "S" "Cables_UTP" "")
(command "-COLOR" "5")
(command "_.PLINE" (list 14000 1150) (list 14000 -20) (list 13860.0 -20) (list 13860.0 -40) "")
(command "-LAYER" "S" "Cables_UTP" "")
(command "-COLOR" "5")
(command "-TEXT" "S" "Standard" "J" "C" (list 14015 565.0) 10 0 "4xUTP")
(command "-LAYER" "S" "Cables_UTP" "")
(command "-COLOR" "5")
(command "_.PLINE" (list 14100 1150) (list 14100 -140) (list 13860.0 -140) (list 13860.0 -160) "")
(command "-LAYER" "S" "Cables_UTP" "")
(command "-COLOR" "5")
(command "-TEXT" "S" "Standard" "J" "C" (list 14115 505.0) 10 0 "2xUTP")
(command "-LAYER" "S" "Cables_UTP" "")
(command "-COLOR" "5")
(command "_.PLINE" (list 14200 1150) (list 14200 -80) (list 13860.0 -80) (list 13860.0 -100) "")
(command "-LAYER" "S" "Cables_UTP" "")
(command "-COLOR" "5")
(command "-TEXT" "S" "Standard" "J" "C" (list 14215 535.0) 10 0 "15xUTP")
(command "-LAYER" "S" "Cables_UTP" "")
(command "-COLOR" "5")
(command "_.PLINE" (list 13800 1350) (list 13800 100) (list 13860.0 100) (list 13860.0 80) "")
(command "-LAYER" "S" "Cables_UTP" "")
(command "-COLOR" "5")
(command "-TEXT" "S" "Standard" "J" "C" (list 13815 725.0) 10 0 "6xUTP")
(command "-LAYER" "S" "Cables_UTP" "")
(command "-COLOR" "5")
(command "_.PLINE" (list 13900 1350) (list 13900 40) (list 13860.0 40) (list 13860.0 20) "")
(command "-LAYER" "S" "Cables_UTP" "")
(command "-COLOR" "5")
(command "-TEXT" "S" "Standard" "J" "C" (list 13915 695.0) 10 0 "7xUTP")
(command "-LAYER" "S" "Cables_UTP" "")
(command "-COLOR" "5")
(command "_.PLINE" (list 14000 1350) (list 14000 -20) (list 13860.0 -20) (list 13860.0 -40) "")
(command "-LAYER" "S" "Cables_UTP" "")
(command "-COLOR" "5")
(command "-TEXT" "S" "Standard" "J" "C" (list 14015 665.0) 10 0 "4xUTP")
(command "-LAYER" "S" "Cables_UTP" "")
(command "-COLOR" "5")
(command "_.PLINE" (list 14100 1350) (list 14100 -140) (list 13860.0 -140) (list 13860.0 -160) "")
(command "-LAYER" "S" "Cables_UTP" "")
(command "-COLOR" "5")
(command "-TEXT" "S" "Standard" "J" "C" (list 14115 605.0) 10 0 "2xUTP")
(command "-LAYER" "S" "Cables_UTP" "")
(command "-COLOR" "5")
(command "_.PLINE" (list 14200 1350) (list 14200 -80) (list 13860.0 -80) (list 13860.0 -100) "")
(command "-LAYER" "S" "Cables_UTP" "")
(command "-COLOR" "5")
(command "-TEXT" "S" "Standard" "J" "C" (list 14215 635.0) 10 0 "15xUTP")
(command "-LAYER" "S" "Cables_UTP" "")
(command "-COLOR" "5")
(command "_.PLINE" (list 13800 1550) (list 13800 100) (list 13860.0 100) (list 13860.0 80) "")
(command "-LAYER" "S" "Cables_UTP" "")
(command "-COLOR" "5")
(command "-TEXT" "S" "Standard" "J" "C" (list 13815 825.0) 10 0 "3xUTP")
(command "-LAYER" "S" "Cables_UTP" "")
(command "-COLOR" "5")
(command "_.PLINE" (list 13900 1550) (list 13900 40) (list 13860.0 40) (list 13860.0 20) "")
(command "-LAYER" "S" "Cables_UTP" "")
(command "-COLOR" "5")
(command "-TEXT" "S" "Standard" "J" "C" (list 13915 795.0) 10 0 "3xUTP")
(command "-LAYER" "S" "Cables_UTP" "")
(command "-COLOR" "5")
(command "_.PLINE" (list 14000 1550) (list 14000 -20) (list 13860.0 -20) (list 13860.0 -40) "")
(command "-LAYER" "S" "Cables_UTP" "")
(command "-COLOR" "5")
(command "-TEXT" "S" "Standard" "J" "C" (list 14015 765.0) 10 0 "2xUTP")
(command "-LAYER" "S" "Cables_UTP" "")
(command "-COLOR" "5")
(command "_.PLINE" (list 14100 1550) (list 14100 -140) (list 13860.0 -140) (list 13860.0 -160) "")
(command "-LAYER" "S" "Cables_UTP" "")
(command "-COLOR" "5")
(command "-TEXT" "S" "Standard" "J" "C" (list 14115 705.0) 10 0 "1xUTP")
(command "-LAYER" "S" "Cables_UTP" "")
(command "-COLOR" "5")
(command "_.PLINE" (list 14200 1550) (list 14200 -80) (list 13860.0 -80) (list 13860.0 -100) "")
(command "-LAYER" "S" "Cables_UTP" "")
(command "-COLOR" "5")
(command "-TEXT" "S" "Standard" "J" "C" (list 14215 735.0) 10 0 "8xUTP")
(command "-LAYER" "S" "Cables_UTP" "")
(command "-COLOR" "5")
(command "_.PLINE" (list 14850 150) (list 14850 -140) (list 14910.0 -140) (list 14910.0 -160) "")
(command "-LAYER" "S" "Cables_UTP" "")
(command "-COLOR" "5")
(command "-TEXT" "S" "Standard" "J" "C" (list 14865 5.0) 10 0 "1xUTP")
(command "-LAYER" "S" "Cables_UTP" "")
(command "-COLOR" "5")
(command "_.PLINE" (list 14950 150) (list 14950 -80) (list 14910.0 -80) (list 14910.0 -100) "")
(command "-LAYER" "S" "Cables_UTP" "")
(command "-COLOR" "5")
(command "-TEXT" "S" "Standard" "J" "C" (list 14965 35.0) 10 0 "2xUTP")
(command "-LAYER" "S" "Cables_UTP" "")
(command "-COLOR" "5")
(command "_.PLINE" (list 14850 350) (list 14850 100) (list 14910.0 100) (list 14910.0 80) "")
(command "-LAYER" "S" "Cables_UTP" "")
(command "-COLOR" "5")
(command "-TEXT" "S" "Standard" "J" "C" (list 14865 225.0) 10 0 "9xUTP")
(command "-LAYER" "S" "Cables_UTP" "")
(command "-COLOR" "5")
(command "_.PLINE" (list 14950 350) (list 14950 40) (list 14910.0 40) (list 14910.0 20) "")
(command "-LAYER" "S" "Cables_UTP" "")
(command "-COLOR" "5")
(command "-TEXT" "S" "Standard" "J" "C" (list 14965 195.0) 10 0 "10xUTP")
(command "-LAYER" "S" "Cables_UTP" "")
(command "-COLOR" "5")
(command "_.PLINE" (list 15050 350) (list 15050 -20) (list 14910.0 -20) (list 14910.0 -40) "")
(command "-LAYER" "S" "Cables_UTP" "")
(command "-COLOR" "5")
(command "-TEXT" "S" "Standard" "J" "C" (list 15065 165.0) 10 0 "6xUTP")
(command "-LAYER" "S" "Cables_UTP" "")
(command "-COLOR" "5")
(command "_.PLINE" (list 15150 350) (list 15150 -140) (list 14910.0 -140) (list 14910.0 -160) "")
(command "-LAYER" "S" "Cables_UTP" "")
(command "-COLOR" "5")
(command "-TEXT" "S" "Standard" "J" "C" (list 15165 105.0) 10 0 "3xUTP")
(command "-LAYER" "S" "Cables_UTP" "")
(command "-COLOR" "5")
(command "_.PLINE" (list 15250 350) (list 15250 -80) (list 14910.0 -80) (list 14910.0 -100) "")
(command "-LAYER" "S" "Cables_UTP" "")
(command "-COLOR" "5")
(command "-TEXT" "S" "Standard" "J" "C" (list 15265 135.0) 10 0 "20xUTP")
(command "-LAYER" "S" "Cables_UTP" "")
(command "-COLOR" "5")
(command "_.PLINE" (list 14850 550) (list 14850 100) (list 14910.0 100) (list 14910.0 80) "")
(command "-LAYER" "S" "Cables_UTP" "")
(command "-COLOR" "5")
(command "-TEXT" "S" "Standard" "J" "C" (list 14865 325.0) 10 0 "8xUTP")
(command "-LAYER" "S" "Cables_UTP" "")
(command "-COLOR" "5")
(command "_.PLINE" (list 14950 550) (list 14950 40) (list 14910.0 40) (list 14910.0 20) "")
(command "-LAYER" "S" "Cables_UTP" "")
(command "-COLOR" "5")
(command "-TEXT" "S" "Standard" "J" "C" (list 14965 295.0) 10 0 "9xUTP")
(command "-LAYER" "S" "Cables_UTP" "")
(command "-COLOR" "5")
(command "_.PLINE" (list 15050 550) (list 15050 -20) (list 14910.0 -20) (list 14910.0 -40) "")
(command "-LAYER" "S" "Cables_UTP" "")
(command "-COLOR" "5")
(command "-TEXT" "S" "Standard" "J" "C" (list 15065 265.0) 10 0 "5xUTP")
(command "-LAYER" "S" "Cables_UTP" "")
(command "-COLOR" "5")
(command "_.PLINE" (list 15150 550) (list 15150 -140) (list 14910.0 -140) (list 14910.0 -160) "")
(command "-LAYER" "S" "Cables_UTP" "")
(command "-COLOR" "5")
(command "-TEXT" "S" "Standard" "J" "C" (list 15165 205.0) 10 0 "3xUTP")
(command "-LAYER" "S" "Cables_UTP" "")
(command "-COLOR" "5")
(command "_.PLINE" (list 15250 550) (list 15250 -80) (list 14910.0 -80) (list 14910.0 -100) "")
(command "-LAYER" "S" "Cables_UTP" "")
(command "-COLOR" "5")
(command "-TEXT" "S" "Standard" "J" "C" (list 15265 235.0) 10 0 "18xUTP")
(command "-LAYER" "S" "Cables_UTP" "")
(command "-COLOR" "5")
(command "_.PLINE" (list 14850 750) (list 14850 100) (list 14910.0 100) (list 14910.0 80) "")
(command "-LAYER" "S" "Cables_UTP" "")
(command "-COLOR" "5")
(command "-TEXT" "S" "Standard" "J" "C" (list 14865 425.0) 10 0 "8xUTP")
(command "-LAYER" "S" "Cables_UTP" "")
(command "-COLOR" "5")
(command "_.PLINE" (list 14950 750) (list 14950 40) (list 14910.0 40) (list 14910.0 20) "")
(command "-LAYER" "S" "Cables_UTP" "")
(command "-COLOR" "5")
(command "-TEXT" "S" "Standard" "J" "C" (list 14965 395.0) 10 0 "9xUTP")
(command "-LAYER" "S" "Cables_UTP" "")
(command "-COLOR" "5")
(command "_.PLINE" (list 15050 750) (list 15050 -20) (list 14910.0 -20) (list 14910.0 -40) "")
(command "-LAYER" "S" "Cables_UTP" "")
(command "-COLOR" "5")
(command "-TEXT" "S" "Standard" "J" "C" (list 15065 365.0) 10 0 "5xUTP")
(command "-LAYER" "S" "Cables_UTP" "")
(command "-COLOR" "5")
(command "_.PLINE" (list 15150 750) (list 15150 -140) (list 14910.0 -140) (list 14910.0 -160) "")
(command "-LAYER" "S" "Cables_UTP" "")
(command "-COLOR" "5")
(command "-TEXT" "S" "Standard" "J" "C" (list 15165 305.0) 10 0 "3xUTP")
(command "-LAYER" "S" "Cables_UTP" "")
(command "-COLOR" "5")
(command "_.PLINE" (list 15250 750) (list 15250 -80) (list 14910.0 -80) (list 14910.0 -100) "")
(command "-LAYER" "S" "Cables_UTP" "")
(command "-COLOR" "5")
(command "-TEXT" "S" "Standard" "J" "C" (list 15265 335.0) 10 0 "18xUTP")
(command "-LAYER" "S" "Cables_UTP" "")
(command "-COLOR" "5")
(command "_.PLINE" (list 14850 950) (list 14850 100) (list 14910.0 100) (list 14910.0 80) "")
(command "-LAYER" "S" "Cables_UTP" "")
(command "-COLOR" "5")
(command "-TEXT" "S" "Standard" "J" "C" (list 14865 525.0) 10 0 "8xUTP")
(command "-LAYER" "S" "Cables_UTP" "")
(command "-COLOR" "5")
(command "_.PLINE" (list 14950 950) (list 14950 40) (list 14910.0 40) (list 14910.0 20) "")
(command "-LAYER" "S" "Cables_UTP" "")
(command "-COLOR" "5")
(command "-TEXT" "S" "Standard" "J" "C" (list 14965 495.0) 10 0 "9xUTP")
(command "-LAYER" "S" "Cables_UTP" "")
(command "-COLOR" "5")
(command "_.PLINE" (list 15050 950) (list 15050 -20) (list 14910.0 -20) (list 14910.0 -40) "")
(command "-LAYER" "S" "Cables_UTP" "")
(command "-COLOR" "5")
(command "-TEXT" "S" "Standard" "J" "C" (list 15065 465.0) 10 0 "5xUTP")
(command "-LAYER" "S" "Cables_UTP" "")
(command "-COLOR" "5")
(command "_.PLINE" (list 15150 950) (list 15150 -140) (list 14910.0 -140) (list 14910.0 -160) "")
(command "-LAYER" "S" "Cables_UTP" "")
(command "-COLOR" "5")
(command "-TEXT" "S" "Standard" "J" "C" (list 15165 405.0) 10 0 "3xUTP")
(command "-LAYER" "S" "Cables_UTP" "")
(command "-COLOR" "5")
(command "_.PLINE" (list 15250 950) (list 15250 -80) (list 14910.0 -80) (list 14910.0 -100) "")
(command "-LAYER" "S" "Cables_UTP" "")
(command "-COLOR" "5")
(command "-TEXT" "S" "Standard" "J" "C" (list 15265 435.0) 10 0 "18xUTP")
(command "-LAYER" "S" "Cables_UTP" "")
(command "-COLOR" "5")
(command "_.PLINE" (list 14850 1150) (list 14850 100) (list 14910.0 100) (list 14910.0 80) "")
(command "-LAYER" "S" "Cables_UTP" "")
(command "-COLOR" "5")
(command "-TEXT" "S" "Standard" "J" "C" (list 14865 625.0) 10 0 "8xUTP")
(command "-LAYER" "S" "Cables_UTP" "")
(command "-COLOR" "5")
(command "_.PLINE" (list 14950 1150) (list 14950 40) (list 14910.0 40) (list 14910.0 20) "")
(command "-LAYER" "S" "Cables_UTP" "")
(command "-COLOR" "5")
(command "-TEXT" "S" "Standard" "J" "C" (list 14965 595.0) 10 0 "9xUTP")
(command "-LAYER" "S" "Cables_UTP" "")
(command "-COLOR" "5")
(command "_.PLINE" (list 15050 1150) (list 15050 -20) (list 14910.0 -20) (list 14910.0 -40) "")
(command "-LAYER" "S" "Cables_UTP" "")
(command "-COLOR" "5")
(command "-TEXT" "S" "Standard" "J" "C" (list 15065 565.0) 10 0 "5xUTP")
(command "-LAYER" "S" "Cables_UTP" "")
(command "-COLOR" "5")
(command "_.PLINE" (list 15150 1150) (list 15150 -140) (list 14910.0 -140) (list 14910.0 -160) "")
(command "-LAYER" "S" "Cables_UTP" "")
(command "-COLOR" "5")
(command "-TEXT" "S" "Standard" "J" "C" (list 15165 505.0) 10 0 "3xUTP")
(command "-LAYER" "S" "Cables_UTP" "")
(command "-COLOR" "5")
(command "_.PLINE" (list 15250 1150) (list 15250 -80) (list 14910.0 -80) (list 14910.0 -100) "")
(command "-LAYER" "S" "Cables_UTP" "")
(command "-COLOR" "5")
(command "-TEXT" "S" "Standard" "J" "C" (list 15265 535.0) 10 0 "18xUTP")
(command "-LAYER" "S" "Cables_UTP" "")
(command "-COLOR" "5")
(command "_.PLINE" (list 14850 1350) (list 14850 100) (list 14910.0 100) (list 14910.0 80) "")
(command "-LAYER" "S" "Cables_UTP" "")
(command "-COLOR" "5")
(command "-TEXT" "S" "Standard" "J" "C" (list 14865 725.0) 10 0 "8xUTP")
(command "-LAYER" "S" "Cables_UTP" "")
(command "-COLOR" "5")
(command "_.PLINE" (list 14950 1350) (list 14950 40) (list 14910.0 40) (list 14910.0 20) "")
(command "-LAYER" "S" "Cables_UTP" "")
(command "-COLOR" "5")
(command "-TEXT" "S" "Standard" "J" "C" (list 14965 695.0) 10 0 "9xUTP")
(command "-LAYER" "S" "Cables_UTP" "")
(command "-COLOR" "5")
(command "_.PLINE" (list 15050 1350) (list 15050 -20) (list 14910.0 -20) (list 14910.0 -40) "")
(command "-LAYER" "S" "Cables_UTP" "")
(command "-COLOR" "5")
(command "-TEXT" "S" "Standard" "J" "C" (list 15065 665.0) 10 0 "5xUTP")
(command "-LAYER" "S" "Cables_UTP" "")
(command "-COLOR" "5")
(command "_.PLINE" (list 15150 1350) (list 15150 -140) (list 14910.0 -140) (list 14910.0 -160) "")
(command "-LAYER" "S" "Cables_UTP" "")
(command "-COLOR" "5")
(command "-TEXT" "S" "Standard" "J" "C" (list 15165 605.0) 10 0 "3xUTP")
(command "-LAYER" "S" "Cables_UTP" "")
(command "-COLOR" "5")
(command "_.PLINE" (list 15250 1350) (list 15250 -80) (list 14910.0 -80) (list 14910.0 -100) "")
(command "-LAYER" "S" "Cables_UTP" "")
(command "-COLOR" "5")
(command "-TEXT" "S" "Standard" "J" "C" (list 15265 635.0) 10 0 "18xUTP")
(command "-LAYER" "S" "Cables_UTP" "")
(command "-COLOR" "5")
(command "_.PLINE" (list 14850 1550) (list 14850 100) (list 14910.0 100) (list 14910.0 80) "")
(command "-LAYER" "S" "Cables_UTP" "")
(command "-COLOR" "5")
(command "-TEXT" "S" "Standard" "J" "C" (list 14865 825.0) 10 0 "4xUTP")
(command "-LAYER" "S" "Cables_UTP" "")
(command "-COLOR" "5")
(command "_.PLINE" (list 14950 1550) (list 14950 40) (list 14910.0 40) (list 14910.0 20) "")
(command "-LAYER" "S" "Cables_UTP" "")
(command "-COLOR" "5")
(command "-TEXT" "S" "Standard" "J" "C" (list 14965 795.0) 10 0 "4xUTP")
(command "-LAYER" "S" "Cables_UTP" "")
(command "-COLOR" "5")
(command "_.PLINE" (list 15050 1550) (list 15050 -20) (list 14910.0 -20) (list 14910.0 -40) "")
(command "-LAYER" "S" "Cables_UTP" "")
(command "-COLOR" "5")
(command "-TEXT" "S" "Standard" "J" "C" (list 15065 765.0) 10 0 "3xUTP")
(command "-LAYER" "S" "Cables_UTP" "")
(command "-COLOR" "5")
(command "_.PLINE" (list 15150 1550) (list 15150 -140) (list 14910.0 -140) (list 14910.0 -160) "")
(command "-LAYER" "S" "Cables_UTP" "")
(command "-COLOR" "5")
(command "-TEXT" "S" "Standard" "J" "C" (list 15165 705.0) 10 0 "2xUTP")
(command "-LAYER" "S" "Cables_UTP" "")
(command "-COLOR" "5")
(command "_.PLINE" (list 15250 1550) (list 15250 -80) (list 14910.0 -80) (list 14910.0 -100) "")
(command "-LAYER" "S" "Cables_UTP" "")
(command "-COLOR" "5")
(command "-TEXT" "S" "Standard" "J" "C" (list 15265 735.0) 10 0 "10xUTP")
(command "-LAYER" "S" "Cables_UTP" "")
(command "-COLOR" "5")
(command "_.PLINE" (list 15900 350) (list 15900 40) (list 15960.0 40) (list 15960.0 20) "")
(command "-LAYER" "S" "Cables_UTP" "")
(command "-COLOR" "5")
(command "-TEXT" "S" "Standard" "J" "C" (list 15915 195.0) 10 0 "2xUTP")
(command "-LAYER" "S" "Cables_UTP" "")
(command "-COLOR" "5")
(command "_.PLINE" (list 16000 350) (list 16000 -20) (list 15960.0 -20) (list 15960.0 -40) "")
(command "-LAYER" "S" "Cables_UTP" "")
(command "-COLOR" "5")
(command "-TEXT" "S" "Standard" "J" "C" (list 16015 165.0) 10 0 "1xUTP")
(command "-LAYER" "S" "Cables_UTP" "")
(command "-COLOR" "5")
(command "_.PLINE" (list 16100 350) (list 16100 -140) (list 15960.0 -140) (list 15960.0 -160) "")
(command "-LAYER" "S" "Cables_UTP" "")
(command "-COLOR" "5")
(command "-TEXT" "S" "Standard" "J" "C" (list 16115 105.0) 10 0 "1xUTP")
(command "-LAYER" "S" "Cables_UTP" "")
(command "-COLOR" "5")
(command "_.PLINE" (list 16200 350) (list 16200 -80) (list 15960.0 -80) (list 15960.0 -100) "")
(command "-LAYER" "S" "Cables_UTP" "")
(command "-COLOR" "5")
(command "-TEXT" "S" "Standard" "J" "C" (list 16215 135.0) 10 0 "4xUTP")
(princ "DONE.")
(princ "\nDibujando cables de Fibra Optica...")
(command "-LAYER" "S" "Fibra_CCTV" "")
(command "-COLOR" "1")
(command "_.LINE" (list 210.0 -240.0) (list 360.0 -610) "")
(command "_.LINE" (list 360.0 -610) (list 15810.0 -610) "")
(command "-LAYER" "S" "Fibra_CCTV" "")
(command "-COLOR" "1")
(command "-TEXT" "S" "Standard" "J" "C" (list 8085.0 -600) 10 0 "15xFO CCTV")
(command "_.LINE" (list 1110.0 -610) (list 1260.0 -180.0) "")
(command "_.LINE" (list 2160.0 -610) (list 2310.0 -180.0) "")
(command "_.LINE" (list 3210.0 -610) (list 3360.0 -180.0) "")
(command "_.LINE" (list 4260.0 -610) (list 4410.0 -180.0) "")
(command "_.LINE" (list 5310.0 -610) (list 5460.0 -180.0) "")
(command "_.LINE" (list 6360.0 -610) (list 6510.0 -180.0) "")
(command "_.LINE" (list 7410.0 -610) (list 7560.0 -180.0) "")
(command "_.LINE" (list 8460.0 -610) (list 8610.0 -180.0) "")
(command "_.LINE" (list 9510.0 -610) (list 9660.0 -180.0) "")
(command "_.LINE" (list 10560.0 -610) (list 10710.0 -180.0) "")
(command "_.LINE" (list 11610.0 -610) (list 11760.0 -180.0) "")
(command "_.LINE" (list 12660.0 -610) (list 12810.0 -180.0) "")
(command "_.LINE" (list 13710.0 -610) (list 13860.0 -180.0) "")
(command "_.LINE" (list 14760.0 -610) (list 14910.0 -180.0) "")
(command "_.LINE" (list 15810.0 -610) (list 15960.0 -180.0) "")
(command "-LAYER" "S" "Fibra_Data" "")
(command "-COLOR" "2")
(command "_.LINE" (list 210.0 -180.0) (list 360.0 -650) "")
(command "_.LINE" (list 360.0 -650) (list 15810.0 -650) "")
(command "-LAYER" "S" "Fibra_Data" "")
(command "-COLOR" "2")
(command "-TEXT" "S" "Standard" "J" "C" (list 8085.0 -640) 10 0 "15xFO DATA")
(command "_.LINE" (list 1110.0 -650) (list 1260.0 -120.0) "")
(command "_.LINE" (list 2160.0 -650) (list 2310.0 -120.0) "")
(command "_.LINE" (list 3210.0 -650) (list 3360.0 -120.0) "")
(command "_.LINE" (list 4260.0 -650) (list 4410.0 -120.0) "")
(command "_.LINE" (list 5310.0 -650) (list 5460.0 -120.0) "")
(command "_.LINE" (list 6360.0 -650) (list 6510.0 -120.0) "")
(command "_.LINE" (list 7410.0 -650) (list 7560.0 -120.0) "")
(command "_.LINE" (list 8460.0 -650) (list 8610.0 -120.0) "")
(command "_.LINE" (list 9510.0 -650) (list 9660.0 -120.0) "")
(command "_.LINE" (list 10560.0 -650) (list 10710.0 -120.0) "")
(command "_.LINE" (list 11610.0 -650) (list 11760.0 -120.0) "")
(command "_.LINE" (list 12660.0 -650) (list 12810.0 -120.0) "")
(command "_.LINE" (list 13710.0 -650) (list 13860.0 -120.0) "")
(command "_.LINE" (list 14760.0 -650) (list 14910.0 -120.0) "")
(command "_.LINE" (list 15810.0 -650) (list 15960.0 -120.0) "")
(command "-LAYER" "S" "Fibra_IPTV" "")
(command "-COLOR" "5")
(command "_.LINE" (list 210.0 -120.0) (list 360.0 -570) "")
(command "_.LINE" (list 360.0 -570) (list 15810.0 -570) "")
(command "-LAYER" "S" "Fibra_IPTV" "")
(command "-COLOR" "5")
(command "-TEXT" "S" "Standard" "J" "C" (list 8085.0 -560) 10 0 "15xFO IPTV")
(command "_.LINE" (list 1110.0 -570) (list 1260.0 -60.0) "")
(command "_.LINE" (list 2160.0 -570) (list 2310.0 -60.0) "")
(command "_.LINE" (list 3210.0 -570) (list 3360.0 -60.0) "")
(command "_.LINE" (list 4260.0 -570) (list 4410.0 -60.0) "")
(command "_.LINE" (list 5310.0 -570) (list 5460.0 -60.0) "")
(command "_.LINE" (list 6360.0 -570) (list 6510.0 -60.0) "")
(command "_.LINE" (list 7410.0 -570) (list 7560.0 -60.0) "")
(command "_.LINE" (list 8460.0 -570) (list 8610.0 -60.0) "")
(command "_.LINE" (list 9510.0 -570) (list 9660.0 -60.0) "")
(command "_.LINE" (list 10560.0 -570) (list 10710.0 -60.0) "")
(command "_.LINE" (list 11610.0 -570) (list 11760.0 -60.0) "")
(command "_.LINE" (list 12660.0 -570) (list 12810.0 -60.0) "")
(command "_.LINE" (list 13710.0 -570) (list 13860.0 -60.0) "")
(command "_.LINE" (list 14760.0 -570) (list 14910.0 -60.0) "")
(command "_.LINE" (list 15810.0 -570) (list 15960.0 -60.0) "")
(command "-LAYER" "S" "Fibra_Telefonia" "")
(command "-COLOR" "4")
(command "_.LINE" (list 210.0 -60.0) (list 360.0 -530) "")
(command "_.LINE" (list 360.0 -530) (list 15810.0 -530) "")
(command "-LAYER" "S" "Fibra_Telefonia" "")
(command "-COLOR" "4")
(command "-TEXT" "S" "Standard" "J" "C" (list 8085.0 -520) 10 0 "15xFO TEL")
(command "_.LINE" (list 1110.0 -530) (list 1260.0 0.0) "")
(command "_.LINE" (list 2160.0 -530) (list 2310.0 0.0) "")
(command "_.LINE" (list 3210.0 -530) (list 3360.0 0.0) "")
(command "_.LINE" (list 4260.0 -530) (list 4410.0 0.0) "")
(command "_.LINE" (list 5310.0 -530) (list 5460.0 0.0) "")
(command "_.LINE" (list 6360.0 -530) (list 6510.0 0.0) "")
(command "_.LINE" (list 7410.0 -530) (list 7560.0 0.0) "")
(command "_.LINE" (list 8460.0 -530) (list 8610.0 0.0) "")
(command "_.LINE" (list 9510.0 -530) (list 9660.0 0.0) "")
(command "_.LINE" (list 10560.0 -530) (list 10710.0 0.0) "")
(command "_.LINE" (list 11610.0 -530) (list 11760.0 0.0) "")
(command "_.LINE" (list 12660.0 -530) (list 12810.0 0.0) "")
(command "_.LINE" (list 13710.0 -530) (list 13860.0 0.0) "")
(command "_.LINE" (list 14760.0 -530) (list 14910.0 0.0) "")
(command "_.LINE" (list 15810.0 -530) (list 15960.0 0.0) "")
(command "-LAYER" "S" "Fibra_WiFi" "")
(command "-COLOR" "3")
(command "_.LINE" (list 210.0 60.0) (list 360.0 -490) "")
(command "_.LINE" (list 360.0 -490) (list 15810.0 -490) "")
(command "-LAYER" "S" "Fibra_WiFi" "")
(command "-COLOR" "3")
(command "-TEXT" "S" "Standard" "J" "C" (list 8085.0 -480) 10 0 "15xFO WIFI")
(command "_.LINE" (list 1110.0 -490) (list 1260.0 60.0) "")
(command "_.LINE" (list 2160.0 -490) (list 2310.0 60.0) "")
(command "_.LINE" (list 3210.0 -490) (list 3360.0 60.0) "")
(command "_.LINE" (list 4260.0 -490) (list 4410.0 60.0) "")
(command "_.LINE" (list 5310.0 -490) (list 5460.0 60.0) "")
(command "_.LINE" (list 6360.0 -490) (list 6510.0 60.0) "")
(command "_.LINE" (list 7410.0 -490) (list 7560.0 60.0) "")
(command "_.LINE" (list 8460.0 -490) (list 8610.0 60.0) "")
(command "_.LINE" (list 9510.0 -490) (list 9660.0 60.0) "")
(command "_.LINE" (list 10560.0 -490) (list 10710.0 60.0) "")
(command "_.LINE" (list 11610.0 -490) (list 11760.0 60.0) "")
(command "_.LINE" (list 12660.0 -490) (list 12810.0 60.0) "")
(command "_.LINE" (list 13710.0 -490) (list 13860.0 60.0) "")
(command "_.LINE" (list 14760.0 -490) (list 14910.0 60.0) "")
(command "_.LINE" (list 15810.0 -490) (list 15960.0 60.0) "")
(princ "DONE.")
(princ "\nDibujando alimentacion desde UPS...")
(command "-LAYER" "S" "UPS" "")
(command "-COLOR" "1")
(command "_.LINE" (list 350.0 -230.0) (list 500.0 -690) "")
(command "_.LINE" (list 500.0 -690) (list 15810.0 -690) "")
(command "_.LINE" (list 1110.0 -690) (list 1260.0 -180.0) "")
(command "_.LINE" (list 1110.0 -690) (list 1260.0 -120.0) "")
(command "_.LINE" (list 1110.0 -690) (list 1260.0 -60.0) "")
(command "_.LINE" (list 1110.0 -690) (list 1260.0 0.0) "")
(command "_.LINE" (list 1110.0 -690) (list 1260.0 60.0) "")
(command "_.LINE" (list 2160.0 -690) (list 2310.0 -180.0) "")
(command "_.LINE" (list 2160.0 -690) (list 2310.0 -120.0) "")
(command "_.LINE" (list 2160.0 -690) (list 2310.0 -60.0) "")
(command "_.LINE" (list 2160.0 -690) (list 2310.0 0.0) "")
(command "_.LINE" (list 2160.0 -690) (list 2310.0 60.0) "")
(command "_.LINE" (list 3210.0 -690) (list 3360.0 -180.0) "")
(command "_.LINE" (list 3210.0 -690) (list 3360.0 -120.0) "")
(command "_.LINE" (list 3210.0 -690) (list 3360.0 -60.0) "")
(command "_.LINE" (list 3210.0 -690) (list 3360.0 0.0) "")
(command "_.LINE" (list 3210.0 -690) (list 3360.0 60.0) "")
(command "_.LINE" (list 4260.0 -690) (list 4410.0 -180.0) "")
(command "_.LINE" (list 4260.0 -690) (list 4410.0 -120.0) "")
(command "_.LINE" (list 4260.0 -690) (list 4410.0 -60.0) "")
(command "_.LINE" (list 4260.0 -690) (list 4410.0 0.0) "")
(command "_.LINE" (list 4260.0 -690) (list 4410.0 60.0) "")
(command "_.LINE" (list 5310.0 -690) (list 5460.0 -180.0) "")
(command "_.LINE" (list 5310.0 -690) (list 5460.0 -120.0) "")
(command "_.LINE" (list 5310.0 -690) (list 5460.0 -60.0) "")
(command "_.LINE" (list 5310.0 -690) (list 5460.0 0.0) "")
(command "_.LINE" (list 5310.0 -690) (list 5460.0 60.0) "")
(command "_.LINE" (list 6360.0 -690) (list 6510.0 -180.0) "")
(command "_.LINE" (list 6360.0 -690) (list 6510.0 -120.0) "")
(command "_.LINE" (list 6360.0 -690) (list 6510.0 -60.0) "")
(command "_.LINE" (list 6360.0 -690) (list 6510.0 0.0) "")
(command "_.LINE" (list 6360.0 -690) (list 6510.0 60.0) "")
(command "_.LINE" (list 7410.0 -690) (list 7560.0 -180.0) "")
(command "_.LINE" (list 7410.0 -690) (list 7560.0 -120.0) "")
(command "_.LINE" (list 7410.0 -690) (list 7560.0 -60.0) "")
(command "_.LINE" (list 7410.0 -690) (list 7560.0 0.0) "")
(command "_.LINE" (list 7410.0 -690) (list 7560.0 60.0) "")
(command "_.LINE" (list 8460.0 -690) (list 8610.0 -180.0) "")
(command "_.LINE" (list 8460.0 -690) (list 8610.0 -120.0) "")
(command "_.LINE" (list 8460.0 -690) (list 8610.0 -60.0) "")
(command "_.LINE" (list 8460.0 -690) (list 8610.0 0.0) "")
(command "_.LINE" (list 8460.0 -690) (list 8610.0 60.0) "")
(command "_.LINE" (list 9510.0 -690) (list 9660.0 -180.0) "")
(command "_.LINE" (list 9510.0 -690) (list 9660.0 -120.0) "")
(command "_.LINE" (list 9510.0 -690) (list 9660.0 -60.0) "")
(command "_.LINE" (list 9510.0 -690) (list 9660.0 0.0) "")
(command "_.LINE" (list 9510.0 -690) (list 9660.0 60.0) "")
(command "_.LINE" (list 10560.0 -690) (list 10710.0 -180.0) "")
(command "_.LINE" (list 10560.0 -690) (list 10710.0 -120.0) "")
(command "_.LINE" (list 10560.0 -690) (list 10710.0 -60.0) "")
(command "_.LINE" (list 10560.0 -690) (list 10710.0 0.0) "")
(command "_.LINE" (list 10560.0 -690) (list 10710.0 60.0) "")
(command "_.LINE" (list 11610.0 -690) (list 11760.0 -180.0) "")
(command "_.LINE" (list 11610.0 -690) (list 11760.0 -120.0) "")
(command "_.LINE" (list 11610.0 -690) (list 11760.0 -60.0) "")
(command "_.LINE" (list 11610.0 -690) (list 11760.0 0.0) "")
(command "_.LINE" (list 11610.0 -690) (list 11760.0 60.0) "")
(command "_.LINE" (list 12660.0 -690) (list 12810.0 -180.0) "")
(command "_.LINE" (list 12660.0 -690) (list 12810.0 -120.0) "")
(command "_.LINE" (list 12660.0 -690) (list 12810.0 -60.0) "")
(command "_.LINE" (list 12660.0 -690) (list 12810.0 0.0) "")
(command "_.LINE" (list 12660.0 -690) (list 12810.0 60.0) "")
(command "_.LINE" (list 13710.0 -690) (list 13860.0 -180.0) "")
(command "_.LINE" (list 13710.0 -690) (list 13860.0 -120.0) "")
(command "_.LINE" (list 13710.0 -690) (list 13860.0 -60.0) "")
(command "_.LINE" (list 13710.0 -690) (list 13860.0 0.0) "")
(command "_.LINE" (list 13710.0 -690) (list 13860.0 60.0) "")
(command "_.LINE" (list 14760.0 -690) (list 14910.0 -180.0) "")
(command "_.LINE" (list 14760.0 -690) (list 14910.0 -120.0) "")
(command "_.LINE" (list 14760.0 -690) (list 14910.0 -60.0) "")
(command "_.LINE" (list 14760.0 -690) (list 14910.0 0.0) "")
(command "_.LINE" (list 14760.0 -690) (list 14910.0 60.0) "")
(command "_.LINE" (list 15810.0 -690) (list 15960.0 -180.0) "")
(command "_.LINE" (list 15810.0 -690) (list 15960.0 -120.0) "")
(command "_.LINE" (list 15810.0 -690) (list 15960.0 -60.0) "")
(command "_.LINE" (list 15810.0 -690) (list 15960.0 0.0) "")
(command "_.LINE" (list 15810.0 -690) (list 15960.0 60.0) "")
(princ "DONE.")

; === FINALIZAR DIBUJO ===
(princ "\nFinalizando y haciendo zoom...")
(command "_.ZOOM" "E")
(command "_.UNDO" "END")
(princ "\n--- PROCESO DE DIBUJO COMPLETADO ---")
